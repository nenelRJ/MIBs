-- File Name : HAISHUO-NMS-MIB-e3_23
-- Date      : Wed Mar 17 10:15:46 CST 2010
-- Author    : AdventNet Agent Toolkit C Edition - MibEditor 6


--
-- HAISHUO-NMS-MIB.mib
-- MIB generated by MG-SOFT Visual MIB Builder Version 5.0  Build 250
-- Wednesday, September 19, 2007 at 09:27:41
--
--  BJGTT-MIB.mib
-- MIB generated by MG-SOFT Visual MIB Builder Version 5.0  Build 250
-- Friday, September 16, 2005 at 10:54:31
--

HAISHUO-TK3723-MIB	DEFINITIONS ::= BEGIN
	IMPORTS
		RowStatus, DisplayString, DateAndTime
			FROM SNMPv2-TC
		sysDescr, sysObjectID, sysUpTime, sysContact, sysName, sysLocation, sysServices, DisplayString
			FROM RFC1213-MIB
		OBJECT-GROUP, NOTIFICATION-GROUP
			FROM SNMPv2-CONF
		enterprises, IpAddress, Integer32, Unsigned32, OBJECT-TYPE, MODULE-IDENTITY, OBJECT-IDENTITY, NOTIFICATION-TYPE, Counter32, Counter64
			FROM SNMPv2-SMI;

	hioso	MODULE-IDENTITY
		LAST-UPDATED	"201111191110"
		ORGANIZATION	"HiOSO NMS."
		CONTACT-INFO	"l386cn@yahoo.com.cn"
		DESCRIPTION		"Revesion for dual port optical!!!"
		REVISION		"201109201720"
		DESCRIPTION		"Revesion for dual port optical."
		::=  {  enterprises  25355  }

	org	OBJECT IDENTIFIER
		::=  {  iso  3  }

	dod	OBJECT IDENTIFIER
		::=  {  org  6  }

	internet	OBJECT IDENTIFIER
		::=  {  dod  1  }

	private	OBJECT IDENTIFIER
		::=  {  internet  4  }

--	enterprises	OBJECT IDENTIFIER
--		::=  {  private  1  }

	universalChassis	OBJECT IDENTIFIER
		::=  {  hioso  3  }

	nmsConformance	OBJECT IDENTIFIER
		::=  {  hioso  256  }

	ucNode	OBJECT IDENTIFIER
		::=  {  universalChassis  1  }

	ucCards	OBJECT IDENTIFIER
		::=  {  universalChassis  2  }

	nmsGroups	OBJECT IDENTIFIER
		::=  {  nmsConformance  1  }

	ucNodeAddress	OBJECT-TYPE	
		SYNTAX			IpAddress
		MAX-ACCESS		read-only
		STATUS			current
		DESCRIPTION		"This is a agent IP address."
		::=  {  ucNode  1  }

	ucNodeNetMask	OBJECT-TYPE	
		SYNTAX			IpAddress
		MAX-ACCESS		read-only
		STATUS			current
		DESCRIPTION		"This is a agent netmask."
		::=  {  ucNode  2  }

	ucNodeGateWay	OBJECT-TYPE	
		SYNTAX			IpAddress
		MAX-ACCESS		read-only
		STATUS			current
		DESCRIPTION		"This is a agent gateway."
		::=  {  ucNode  3  }

	ucNodeTrapEnable	OBJECT-TYPE	
		SYNTAX			INTEGER  { enable ( 1 ) , disable ( 2 ) } 
		MAX-ACCESS		read-write
		STATUS			current
		DESCRIPTION		"The agent could send trap or not."
		::=  {  ucNode  4  }

	ucNodeTrapSink	OBJECT-TYPE	
		SYNTAX			IpAddress
		MAX-ACCESS		read-write
		STATUS			current
		DESCRIPTION		"This is trapsink address.
				Agent will send trap to this address."
		::=  {  ucNode  5  }

	ucNodeTempAlarmThreshold	OBJECT-TYPE	
		SYNTAX			Integer32  ( 20 .. 99  ) 
		MAX-ACCESS		read-write
		STATUS			current
		DESCRIPTION		"The alarm threshold of the chassis temperature."
		::=  {  ucNode  6  }

	ucNodeSet	OBJECT-TYPE	
		SYNTAX			INTEGER  { nop ( 0 ) , reboot ( 1 ) , resetAll ( 2 ) , recoverAll ( 3 ) } 
		MAX-ACCESS		read-write
		STATUS			current
		DESCRIPTION		"Description."
		::=  {  ucNode  7  }

	ucChassis	OBJECT IDENTIFIER
		::=  {  ucNode  8  }

	ucSlot	OBJECT IDENTIFIER
		::=  {  ucNode  9  }

	ucSystem	OBJECT IDENTIFIER
		::=  {  ucNode  11  }

	ucSoftware	OBJECT IDENTIFIER
		::=  {  ucNode  12  }

	ucSnmpApp	OBJECT IDENTIFIER
		::=  {  ucNode  13  }

	ucPon	OBJECT IDENTIFIER
		::=  {  ucCards  6  }

--	currentObjectGroup	OBJECT-GROUP
--		OBJECTS			{ ucNodeAddress, ucNodeNetMask, ucNodeGateWay, ucNodeTrapEnable, ucNodeTrapSink, ucNodeTempAlarmThreshold, ucNodeSet, ucCvtSlotIndex, ucCvtTpColCount, ucCvtFxColCount, ucCvtRStatus, ucCvtRFxSD, ucCvtRTpAuto, ucChsSet, ucSlotCardSN, ucSlotSet, ucCvtTpRevpak, ucCvtTpErrPak, ucCvtTpDropPak, ucCvtFxRevPak, ucCvtFxErrPak, ucCvtFxDropPak, ucCvtTpAuto, ucCvtTpSpd, ucCvtTpDuplex, ucCvtTpfFlowCtrl, ucCvtTpLink, ucCvtFxDuplex, ucCvtFxLink, ucCvtTpInRate, ucCvtTpOutRate, ucCvtRTpLink, ucCvtRSpd, ucCvtRTpDuplex, ucCvtLoopbakStat, ucCvtLoopbakResult, ucSlotIndex, ucSlotStatus, ucSlotCardType, ucGvtSlotIndex, ucGvtLoopbakStat, ucGvtLoopbakResult, ucGvtTpLink, ucGvtTpSpd, ucGvtTpDuplex, ucGvtTpAuto, ucGvtTpfFlowCtrl, ucGvtTpInRate, ucGvtTpOutRate, ucGvtTpRevpak, ucGvtTpErrPak, ucGvtTpDropPak, ucGvtTpColCount, ucGvtFxLink, ucGvtFxDuplex, ucGvtFxRevPak, ucGvtFxErrPak, ucGvtFxDropPak, ucGvtFxColCount, ucGvtRStatus, ucGvtRFxSD, ucGvtRTpLink, ucGvtRSpd, ucGvtRTpDuplex, ucGvtRTpAuto, ucChsExist, ucChsIndex, ucChsSN,



























-- ucChsTmp, ucChsFana, ucChsFanb, ucChsPwa, ucChsPwb }
--		STATUS			current
--		DESCRIPTION		"Enter the description of the created OBJECT-GROUP."
--		::=  {  nmsGroups  1  }

--	currentNotificationGroup	NOTIFICATION-GROUP
--		NOTIFICATIONS	{ ucGvtStatusTrap, ucGvtTpLnkTrap, ucGvtFxLnkTrap, ucGvtRStatusTrap, ucGvtRFxLnkTrap, ucGvtRTpLnkTrap, ucCvtStatusTrap, ucCvtTpLnkTrap, ucCvtFxLnkTrap, ucCvtRStatusTrap, ucCvtRFxLnkTrap, ucCvtRTpLnkTrap, ucChsFanaTrap, ucChsFanbTrap, ucChsPwaTrap, ucChsPwbTrap, ucChsTmpTrap, ucSlotNewCardTrap, ucSlotLostCardTrap, ucChsExistTrap }
--		STATUS			current
--		DESCRIPTION		"Description."
--		::=  {  nmsGroups  2  }

	ucChsTable	OBJECT-TYPE
		SYNTAX		SEQUENCE  OF  UcChsEntry
		MAX-ACCESS	not-accessible
		STATUS		current
		DESCRIPTION	"Chassis Card information table."
		::=  { ucChassis  1 }

	ucChsEntry	OBJECT-TYPE
		SYNTAX		UcChsEntry
		MAX-ACCESS	not-accessible
		STATUS		current
		DESCRIPTION	"Chassis Card information entry."
		INDEX		{  ucChsIndex  }
		::=  { ucChsTable 1 }

	UcChsEntry  ::=  SEQUENCE {
		ucChsIndex  Integer32,
		ucChsSN  DisplayString,
		ucChsExist  INTEGER,
		ucChsTmp  Integer32,
		ucChsFana  INTEGER,
		ucChsFanb  INTEGER,
		ucChsPwa  INTEGER,
		ucChsPwb  INTEGER,
		ucChsSet  INTEGER,
		ucChsAuthCtrl  INTEGER
		}


	ucChsIndex	OBJECT-TYPE	
		SYNTAX			Integer32  ( 1 .. 4  ) 
		MAX-ACCESS		read-only
		STATUS			current
		DESCRIPTION		"Reference index for chassis card."
		::=  {  ucChsEntry  1  }


	ucChsSN	OBJECT-TYPE	
		SYNTAX			DisplayString
		MAX-ACCESS		read-only
		STATUS			current
		DESCRIPTION		"Chassis card serial number."
		::=  {  ucChsEntry  2  }


	ucChsExist	OBJECT-TYPE	
		SYNTAX			INTEGER  { exist ( 1 ) , notExist ( 2 ) } 
		MAX-ACCESS		read-only
		STATUS			current
		DESCRIPTION		"Description."
		::=  {  ucChsEntry  3  }


	ucChsTmp	OBJECT-TYPE	
		SYNTAX			Integer32
		MAX-ACCESS		read-only
		STATUS			current
		DESCRIPTION		"The chassis temperature."
		::=  {  ucChsEntry  4  }


	ucChsFana	OBJECT-TYPE	
		SYNTAX			INTEGER  { notExist ( 0 ) , normal ( 1 ) , warning ( 2 ) , alarm ( 3 ) } 
		MAX-ACCESS		read-only
		STATUS			current
		DESCRIPTION		"Fan Status."
		::=  {  ucChsEntry  5  }


	ucChsFanb	OBJECT-TYPE	
		SYNTAX			INTEGER  { notExist ( 0 ) , normal ( 1 ) , warning ( 2 ) , alarm ( 3 ) } 
		MAX-ACCESS		read-only
		STATUS			current
		DESCRIPTION		"Fan Status."
		::=  {  ucChsEntry  6  }


	ucChsPwa	OBJECT-TYPE	
		SYNTAX			INTEGER  { notExist ( 0 ) , normal ( 1 ) , abnormal ( 2 ) } 
		MAX-ACCESS		read-only
		STATUS			current
		DESCRIPTION		"The chassis power supply status."
		::=  {  ucChsEntry  7  }


	ucChsPwb	OBJECT-TYPE	
		SYNTAX			INTEGER  { notExist ( 0 ) , normal ( 1 ) , abnormal ( 2 ) } 
		MAX-ACCESS		read-only
		STATUS			current
		DESCRIPTION		"The chassis power supply status."
		::=  {  ucChsEntry  8  }


	ucChsSet	OBJECT-TYPE	
		SYNTAX			INTEGER  -- { nop ( 0 ) , recoverChassisDefault ( 1 ) , resetAllSlots ( 2 ) , recoverAllSlotDefault ( 3 ) } 
		MAX-ACCESS		read-write
		STATUS			current
		DESCRIPTION		"Set chassis temperature threadhold value for trap high-temperature alarm"
		::=  {  ucChsEntry  9  }
		
	ucChsAuthCtrl	OBJECT-TYPE	
		SYNTAX			INTEGER  { disableAuth(0) ,enableAuth( 1 ) } 
		MAX-ACCESS		read-write
		STATUS			current
		DESCRIPTION		"Control for link register"
		::=  {  ucChsEntry  10  }	
		

	ucChassisTrap	OBJECT IDENTIFIER
		::=  {  ucChassis  2  }
		
		
-- the table for auth link access function,2014.01.17 Alinsion		
	ucAuthMacGroupTable	OBJECT-TYPE
		SYNTAX		SEQUENCE  OF  UcAuthMacGroupEntry
		MAX-ACCESS	not-accessible
		STATUS		current
		DESCRIPTION	"The Link Mac Groups,Which Can Register Epon Network System,When Auth Function Enable"
		::=  { ucChassis  3 }

	ucAuthMacGroupEntry	OBJECT-TYPE
		SYNTAX		UcAuthMacGroupEntry
		MAX-ACCESS	not-accessible
		STATUS		current
		DESCRIPTION	""
		INDEX		{  ucAuthMacGroupIndex  }
		::=  { ucAuthMacGroupTable 1 }

	UcAuthMacGroupEntry  ::=  SEQUENCE {
		ucAuthMacGroupIndex  Integer32,
		ucAuthMacGroupInfo   DisplayString
		}

	ucAuthMacGroupIndex	OBJECT-TYPE	
		SYNTAX			Integer32  ( 1 .. 9  ) 
		MAX-ACCESS	read-only
		STATUS			current
		DESCRIPTION		"Reference index for chassis card."
		::=  {  ucAuthMacGroupEntry  1  }


	ucAuthMacGroupInfo	OBJECT-TYPE	
		SYNTAX			DisplayString ( SIZE (0 .. 6))
		MAX-ACCESS  read-write
		STATUS			current
		DESCRIPTION		"The first row is the default auth mac group, can not be modify"
		::=  {  ucAuthMacGroupEntry  2  }
		
				
		

	ucSlotTable	OBJECT-TYPE
		SYNTAX		SEQUENCE  OF  UcSlotEntry
		MAX-ACCESS	not-accessible
		STATUS		current
		DESCRIPTION	"Description."
		::=  { ucSlot  1 }

	ucSlotEntry	OBJECT-TYPE
		SYNTAX		UcSlotEntry
		MAX-ACCESS	not-accessible
		STATUS		current
		DESCRIPTION	"Description."
		INDEX		{  ucSlotIndex  }
		::=  { ucSlotTable 1 }

	UcSlotEntry  ::=  SEQUENCE {
		ucSlotIndex  Integer32,
		ucSlotStatus  INTEGER,
		ucSlotCardType  INTEGER,
		ucSlotCardSN  DisplayString,
		ucSlotSet  INTEGER
		}


	ucSlotIndex	OBJECT-TYPE	
		SYNTAX			Integer32  ( 1 .. 64  ) 
		MAX-ACCESS		read-only
		STATUS			current
		DESCRIPTION		"Description."
		::=  {  ucSlotEntry  1  }


	ucSlotStatus	OBJECT-TYPE	
		SYNTAX			INTEGER  { notExist ( 0 ) , enabled ( 1 ) , disabled ( 2 ) , deniedAndDisabled ( 3 ) } 
		MAX-ACCESS		read-only
		STATUS			current
		DESCRIPTION		"Description."
		::=  {  ucSlotEntry  2  }


	ucSlotCardType	OBJECT-TYPE	
		SYNTAX			INTEGER  { 
				threeRLineCard ( 1 ) , 
				twoPlusOneSwitch ( 2 ) , 
				coverterV2 ( 3 ) , 
				fastEthernetSwitch ( 4 ) , 
				gigaconverterV2 ( 5 ) , 
				eponolttype3721 ( 6 ) , 
				cascadeChassis ( 7 ) , 
				cascadeCoverterV2 ( 8 ) , 
				cascadeGigaconverterV2 ( 9 ) , 
				cascade ( 10 ) ,   
				eponolttype3723 ( 11 ) ,
				unknown ( 255 ) } 
		MAX-ACCESS		read-only
		STATUS			current
		DESCRIPTION		"Description."
		::=  {  ucSlotEntry  3  }


	ucSlotCardSN	OBJECT-TYPE	
		SYNTAX			DisplayString
		MAX-ACCESS		read-only
		STATUS			current
		DESCRIPTION		"Description."
		::=  {  ucSlotEntry  4  }


	ucSlotSet	OBJECT-TYPE	
		SYNTAX			INTEGER  { nop ( 0 ) , enable ( 1 ) , disable ( 2 ) , reset ( 3 ) , recoverDefault ( 4 ) } 
		MAX-ACCESS		read-write
		STATUS			current
		DESCRIPTION		"Description."
		::=  {  ucSlotEntry  5  }

	ucSlotTrap	OBJECT IDENTIFIER
		::=  {  ucSlot  2  }
		
		


-- ==============================================================================================		
	ucSnmpAppTable	OBJECT-TYPE
		SYNTAX		SEQUENCE  OF  UcSnmpAppEntry
		MAX-ACCESS	not-accessible
		STATUS		current
		DESCRIPTION	"Description."
		::=  { ucSnmpApp  1 }

	ucSnmpAppEntry	OBJECT-TYPE
		SYNTAX		UcSnmpAppEntry
		MAX-ACCESS	not-accessible
		STATUS		current
		DESCRIPTION	"Description."
		INDEX		{  ucSnmpAppIndex  }
		::=  { ucSnmpAppTable 1 }

	UcSnmpAppEntry  ::=  SEQUENCE {
		ucSnmpAppIndex  	Integer32,
		ucSnmpAppVersion  	DisplayString,
		ucSnmpAppDate      DisplayString,
		ucSnmpAppUpgrade   DisplayString,
		ucSnmpAppUpgradeStatus		INTEGER,
		ucSnmpAppCommand   OCTET STRING
		}


	ucSnmpAppIndex	OBJECT-TYPE	
		SYNTAX			Integer32  ( 1 .. 64  ) 
		MAX-ACCESS		read-only
		STATUS			current
		DESCRIPTION		"Description."
		::=  {  ucSnmpAppEntry  1  }


	ucSnmpAppVersion	OBJECT-TYPE	
		SYNTAX			DisplayString
		MAX-ACCESS		read-only
		STATUS			current
		DESCRIPTION		"Description."
		::=  {  ucSnmpAppEntry  2  }


	ucSnmpAppDate	OBJECT-TYPE	
		SYNTAX			DisplayString
		MAX-ACCESS		read-only
		STATUS			current
		DESCRIPTION		"Description."
		::=  {  ucSnmpAppEntry  3  }


	ucSnmpAppUpgrade	OBJECT-TYPE	
		SYNTAX			OCTET STRING (SIZE(1..64))
		MAX-ACCESS		read-write
		STATUS			current
		DESCRIPTION		"Description."
		::=  {  ucSnmpAppEntry  4  }

	ucSnmpAppUpgradeStatus	OBJECT-TYPE	
		SYNTAX			INTEGER {
				upgrade_normal(0),
				upgrade_start(1),
				upgrade_downloading(2),
				upgrade_downloadfaild(3),
				upgrade_checkfile(4),
				upgrade_fileerror(5),
				upgrade_success(6)
		} 
		MAX-ACCESS		read-only
		STATUS				current
		DESCRIPTION		"Description."
		::=  {  ucSnmpAppEntry  5  }		
		    
	ucSnmpAppCommand	OBJECT-TYPE	
		SYNTAX			OCTET STRING (SIZE(1..128))
		MAX-ACCESS		read-write
		STATUS			current
		DESCRIPTION		"Send command from this node to manage card"
		::=  {  ucSnmpAppEntry  6  }		    
		
-- ==============================================================================================		
		

	uccmd	OBJECT IDENTIFIER
		::=  {  ucSystem  1  }

	ucntp	OBJECT IDENTIFIER
		::=  {  ucSystem  2  }

	ucLog	OBJECT IDENTIFIER
		::=  {  ucSystem  3  }

	ucSyswareNmsType	OBJECT-TYPE	
		SYNTAX			INTEGER  { none ( 0 ) , boot ( 1 ) , k1 ( 2 ) , r1 ( 3 ) , k2 ( 4 ) , r2 ( 5 ) , snmp ( 6 ) , config ( 7 ) , all ( 8 ) } 
		MAX-ACCESS		read-write
		STATUS			current
		DESCRIPTION		"Description."
		::=  {  ucSoftware  1  }

	ucSyswareNmsFileSize	OBJECT-TYPE	
		SYNTAX			Integer32  ( 0 .. 4096  ) 
		MAX-ACCESS		read-write
		STATUS			current
		DESCRIPTION		"Description."
		::=  {  ucSoftware  2  }

	ucSyswareNmsFilePath	OBJECT-TYPE	
		SYNTAX			DisplayString
		MAX-ACCESS		read-write
		STATUS			current
		DESCRIPTION		"Description."
		::=  {  ucSoftware  3  }

	ucSyswareNmsState	OBJECT-TYPE	
		SYNTAX			INTEGER  { running ( 0 ) , updating ( 1 ) } 
		MAX-ACCESS		read-write
		STATUS			current
		DESCRIPTION		"Description."
		::=  {  ucSoftware  4  }

	ucSyswareNmsServerIP	OBJECT-TYPE	
		SYNTAX			IpAddress
		MAX-ACCESS		read-write
		STATUS			current
		DESCRIPTION		""
		::=  {  ucSoftware  5  }

	ucSyswareNmsServerPort	OBJECT-TYPE	
		SYNTAX			Integer32  ( 0 .. 65535  ) 
		MAX-ACCESS		read-write
		STATUS			current
		DESCRIPTION		""
		::=  {  ucSoftware  6  }

	ucSyswareNmsServerLogin	OBJECT-TYPE	
		SYNTAX			DisplayString  ( SIZE ( 0 .. 32  ) ) 
		MAX-ACCESS		read-write
		STATUS			current
		DESCRIPTION		""
		::=  {  ucSoftware  7  }

	ucSyswareNmsServerPassword	OBJECT-TYPE	
		SYNTAX			DisplayString  ( SIZE ( 0 .. 32  ) ) 
		MAX-ACCESS		read-write
		STATUS			current
		DESCRIPTION		""
		::=  {  ucSoftware  8  }

	ucSyswareNmsServerResult	OBJECT-TYPE	
		SYNTAX			DisplayString  ( SIZE ( 0 .. 32  ) ) 
		MAX-ACCESS		read-write
		STATUS			current
		DESCRIPTION		""
		::=  {  ucSoftware  9  }

	ucPonPort	OBJECT IDENTIFIER
		::=  {  ucPon  1  }

	ucOperaPara	OBJECT IDENTIFIER
		::=  {  ucPon  2  }

	ucBoardCfg	OBJECT IDENTIFIER
		::=  {  ucPon  3  }

	ucEthernet	OBJECT IDENTIFIER
		::=  {  ucPon  4  }

	ucPerformance	OBJECT IDENTIFIER
		::=  {  ucPon  5  }

	ucAlarmMgmt	OBJECT IDENTIFIER
		::=  {  ucPon  6  }

	ucAuthentication	OBJECT IDENTIFIER
		::=  {  ucPon  7  }

	ucLayer3	OBJECT IDENTIFIER
		::=  {  ucPon  8  }

	ucSTP	OBJECT IDENTIFIER
		::=  {  ucPon  9  }

	ucPonTrap	OBJECT IDENTIFIER
		::=  {  ucPon  10  }

	ucNMS	OBJECT IDENTIFIER
		::=  {  ucPon  11  }
                                 
                                
	ucChassisTrapV2	OBJECT-IDENTITY
		STATUS			current
		DESCRIPTION		"System Traps."
		::=  {  ucChassisTrap  1  }

	ucSlotTrapV2	OBJECT-IDENTITY
		STATUS			current
		DESCRIPTION		"System Traps."
		::=  {  ucSlotTrap  1  }

	ucCMD	OBJECT-TYPE	
		SYNTAX			DisplayString  ( SIZE ( 0 .. 255  ) ) 
		MAX-ACCESS		read-write
		STATUS			current
		DESCRIPTION		"Description"
		::=  {  uccmd  1  }

	ucCMDResult	OBJECT-TYPE	
		SYNTAX			DisplayString  ( SIZE ( 0 .. 255  ) ) 
		MAX-ACCESS		read-only
		STATUS			current
		DESCRIPTION		"Description"
		::=  {  uccmd  2  }

	ucntpServerIP	OBJECT-TYPE	
		SYNTAX			IpAddress
		MAX-ACCESS		read-write
		STATUS			current
		DESCRIPTION		"Discription
Mn ?e?? 0@."
		::=  {  ucntp  1  }

	ucntpEnable	OBJECT-TYPE	
		SYNTAX			INTEGER  { enable ( 0 ) , disable ( 1 ) } 
		MAX-ACCESS		read-write
		STATUS			current
		DESCRIPTION		"Description"
		::=  {  ucntp  2  }

	ucClearLoggingAlarm	OBJECT-TYPE	
		SYNTAX			INTEGER  { nop ( 0 ) , clear ( 1 ) } 
		MAX-ACCESS		read-write
		STATUS			current
		DESCRIPTION		"clear Logging alarm Buffer"
		::=  {  ucLog  1  }

	ucClearLoggingCommand	OBJECT-TYPE	
		SYNTAX			INTEGER  { nop ( 0 ) , clear ( 1 ) } 
		MAX-ACCESS		read-write
		STATUS			current
		DESCRIPTION		"clear logging command buffer"
		::=  {  ucLog  2  }

	ucClearLoggingSnmp	OBJECT-TYPE	
		SYNTAX			INTEGER  { nop ( 0 ) , clear ( 1 ) } 
		MAX-ACCESS		read-write
		STATUS			current
		DESCRIPTION		"clear logging snmp buffer"
		::=  {  ucLog  3  }

	ucLoggingBufferSize	OBJECT-TYPE	
		SYNTAX			Integer32  ( 100 .. 1000  ) 
		MAX-ACCESS		read-write
		STATUS			current
		DESCRIPTION		"set logging alarm buffer size,
default:200,range:100..1000,
0=close"
		::=  {  ucLog  4  }

	ucLoggingConsole	OBJECT-TYPE	
		SYNTAX			INTEGER  { off ( 0 ) , major ( 1 ) , minor ( 2 ) , warnings ( 3 ) , indeterminate ( 4 ) , cleared ( 5 ) , notifications ( 6 ) } 
		MAX-ACCESS		read-write
		STATUS			current
		DESCRIPTION		"set sending alarm to the console or telnet terminal,
initial level:notifications"
		::=  {  ucLog  5  }

	ucLogfilesave	OBJECT IDENTIFIER
		::=  {  ucLog  6  }

	ucLogFtp	OBJECT IDENTIFIER
		::=  {  ucLog  7  }

	ucLogLevel	OBJECT-TYPE	
		SYNTAX			INTEGER  { off ( 0 ) , major ( 1 ) , minor ( 2 ) , warnings ( 3 ) , indeterminate ( 4 ) , cleared ( 5 ) , notifications ( 6 ) } 
		MAX-ACCESS		read-write
		STATUS			current
		DESCRIPTION		"the logging level of the local record"
		::=  {  ucLog  8  }

	ucLogCmdlogInterval	OBJECT-TYPE	
		SYNTAX			Integer32  ( 10 .. 65535  ) 
		MAX-ACCESS		read-write
		STATUS			current
		DESCRIPTION		"the time interval of saving the cmd log.
0=off."
		::=  {  ucLog  9  }

	ucLogSnmplogInterval	OBJECT-TYPE	
		SYNTAX			Integer32  ( 10 .. 65535  ) 
		MAX-ACCESS		read-write
		STATUS			current
		DESCRIPTION		"the time interval of saving the snmp log.
0=off."
		::=  {  ucLog  10  }

	ucLogSave	OBJECT-TYPE	
		SYNTAX			INTEGER  { disable ( 0 ) , enable ( 1 ) } 
		MAX-ACCESS		read-write
		STATUS			current
		DESCRIPTION		"open or close the cmd/snmp logging function"
		::=  {  ucLog  11  }

	ucLogOn	OBJECT-TYPE	
		SYNTAX			INTEGER  { disable ( 0 ) , enable ( 1 ) } 
		MAX-ACCESS		read-write
		STATUS			current
		DESCRIPTION		"open or close the logging function.
if the logging on == disable,then the logging mode,logging console,logging buffer,logging level,logging ftp,logging trap,logging filesavetime will have no effect."
		::=  {  ucLog  12  }

	ucSyslog	OBJECT IDENTIFIER
		::=  {  ucLog  13  }

	ucOltPortLNPTable	OBJECT-TYPE
		SYNTAX		SEQUENCE  OF  UcOltPortLNPEntry
		MAX-ACCESS	not-accessible
		STATUS		current
		DESCRIPTION	"Description"
		::=  { ucPonPort  1 }

	ucOltPortLNPEntry	OBJECT-TYPE
		SYNTAX		UcOltPortLNPEntry
		MAX-ACCESS	not-accessible
		STATUS		current
		DESCRIPTION	"Description"
		INDEX		{  ucLNPslotIndex, ucLNPPonIndex, ucLNPPortIndex  }
		::=  { ucOltPortLNPTable 1 }

	UcOltPortLNPEntry  ::=  SEQUENCE {
		ucLNPslotIndex  Integer32,
		ucLNPPonIndex  Integer32,
		ucLNPPortIndex  Integer32,
		ucLNPSpd  INTEGER,
		ucLNPDup  INTEGER,
		ucLNPFC  INTEGER,
		ucLNPAN  INTEGER,
		ucLNPLenErrMode  INTEGER,
		ucLNPPortStat  INTEGER,
		ucLNPLinkStat  INTEGER,
		ucLNPPortState  DisplayString,
		ucLNPPortName  DisplayString
		}


	ucLNPslotIndex	OBJECT-TYPE	
		SYNTAX			Integer32  ( 1 .. 16  ) 
		MAX-ACCESS		read-only
		STATUS			current
		DESCRIPTION		"Description."
		::=  {  ucOltPortLNPEntry  1  }


	ucLNPPonIndex	OBJECT-TYPE	
		SYNTAX			Integer32  ( 1 .. 32  ) 
		MAX-ACCESS		read-only
		STATUS			current
		DESCRIPTION		"Description."
		::=  {  ucOltPortLNPEntry  2  }


	ucLNPPortIndex	OBJECT-TYPE	
		SYNTAX			Integer32  ( 1 .. 25  ) 
		MAX-ACCESS		read-only
		STATUS			current
		DESCRIPTION		"Description."
		::=  {  ucOltPortLNPEntry  3  }


	ucLNPSpd	OBJECT-TYPE	
		SYNTAX			INTEGER  { bw10M ( 1 ) , bw100M ( 2 ) , bw1000M ( 3 ) , bw1GU2GD ( 4 ) } 
		MAX-ACCESS		read-write
		STATUS			obsolete
		DESCRIPTION		"Speed
                  10 Mbps/100 Mbps/1G (1000 Mbps)/2G downstream, 1G upstream"
		::=  {  ucOltPortLNPEntry  4  }


	ucLNPDup	OBJECT-TYPE	
		SYNTAX			INTEGER  { halfdup ( 1 ) , fulldup ( 2 ) } 
		MAX-ACCESS		read-write
		STATUS			obsolete
		DESCRIPTION		"Duplex."
		::=  {  ucOltPortLNPEntry  5  }


	ucLNPFC	OBJECT-TYPE	
		SYNTAX			INTEGER  { disabled ( 1 ) , enabled ( 2 ) } 
		MAX-ACCESS		read-write
		STATUS			obsolete
		DESCRIPTION		"Flow Control."
		::=  {  ucOltPortLNPEntry  6  }


	ucLNPAN	OBJECT-TYPE	
		SYNTAX			INTEGER  { disabled ( 1 ) , enabled ( 2 ) } 
		MAX-ACCESS		read-write
		STATUS			obsolete
		DESCRIPTION		"Auto Negotiation Enable."
		::=  {  ucOltPortLNPEntry  7  }


	ucLNPLenErrMode	OBJECT-TYPE	
		SYNTAX			INTEGER  { pass ( 1 ) , discard ( 2 ) } 
		MAX-ACCESS		read-write
		STATUS			obsolete
		DESCRIPTION		"Length error discard
                  1 = count the errors but allow the frames to pass,
                  2 = discard frames with length errors."
		::=  {  ucOltPortLNPEntry  8  }


	ucLNPPortStat	OBJECT-TYPE	
		SYNTAX			INTEGER  { disabled ( 1 ) , enabled ( 2 ) } 
		MAX-ACCESS		read-write
		STATUS			obsolete
		DESCRIPTION		"Description."
		::=  {  ucOltPortLNPEntry  9  }


	ucLNPLinkStat	OBJECT-TYPE	
		SYNTAX			INTEGER  { down ( 1 ) , up ( 2 ) } 
		MAX-ACCESS		read-only
		STATUS			obsolete
		DESCRIPTION		"Description."
		::=  {  ucOltPortLNPEntry  10  }


	ucLNPPortState	OBJECT-TYPE	
		SYNTAX			DisplayString  ( SIZE ( 0 .. 255  ) ) 
		MAX-ACCESS		read-write
		STATUS			current
		DESCRIPTION		"size  Description
1    speed (0=10, 1=100, 2=1000 Mbps )
1    duplex(0=Half,1=Full)
1    flowCtrlEnabled(1=Enabled, 0=Disabled)
1    autoNegEnabled(1=Enabled, 0=Disabled)
1    lenErrDiscard(1=Discard, 0=Allow)
1    enabled(1=Enabled, 0=Disabled)
1    linkUp(1=up,0=down)"
		::=  {  ucOltPortLNPEntry  11  }


	ucLNPPortName	OBJECT-TYPE	
		SYNTAX			DisplayString  ( SIZE ( 0 .. 32  ) ) 
		MAX-ACCESS		read-write
		STATUS			current
		DESCRIPTION		"Description"
		::=  {  ucOltPortLNPEntry  12  }

	ucOnuPortUSRTable	OBJECT-TYPE
		SYNTAX		SEQUENCE  OF  UcOnuPortUSREntry
		MAX-ACCESS	not-accessible
		STATUS		current
		DESCRIPTION	"Description"
		::=  { ucPonPort  2 }

	ucOnuPortUSREntry	OBJECT-TYPE
		SYNTAX		UcOnuPortUSREntry
		MAX-ACCESS	not-accessible
		STATUS		current
		DESCRIPTION	"Description"
		INDEX		{  ucUSRslotIndex, ucUSRPonIndex, ucUSRONUIndex, ucUSRPortIndex  }
		::=  { ucOnuPortUSRTable 1 }

	UcOnuPortUSREntry  ::=  SEQUENCE {
		ucUSRslotIndex  Integer32,
		ucUSRPonIndex  Integer32,
		ucUSRONUIndex  Integer32,
		ucUSRPortIndex  Integer32,
		ucUSRPortState  DisplayString,
		ucUSRPortRateCtrlIngress  DisplayString,
		ucUSRPortRateCtrlEgress  DisplayString,
		ucUSRPortName  DisplayString
		}


	ucUSRslotIndex	OBJECT-TYPE	
		SYNTAX			Integer32  ( 1 .. 16  ) 
		MAX-ACCESS		read-only
		STATUS			current
		DESCRIPTION		"Description."
		::=  {  ucOnuPortUSREntry  1  }


	ucUSRPonIndex	OBJECT-TYPE	
		SYNTAX			Integer32  ( 1 .. 32  ) 
		MAX-ACCESS		read-only
		STATUS			current
		DESCRIPTION		"Description."
		::=  {  ucOnuPortUSREntry  2  }


	ucUSRONUIndex	OBJECT-TYPE	
		SYNTAX			Integer32  ( 1 .. 256  ) 
		MAX-ACCESS		read-only
		STATUS			current
		DESCRIPTION		"Description."
		::=  {  ucOnuPortUSREntry  3  }


	ucUSRPortIndex	OBJECT-TYPE	
		SYNTAX			Integer32  ( 1 .. 25  ) 
		MAX-ACCESS		read-only
		STATUS			current
		DESCRIPTION		"Description."
		::=  {  ucOnuPortUSREntry  4  }


	ucUSRPortState	OBJECT-TYPE	
		SYNTAX			DisplayString  ( SIZE ( 7 .. 7  ) ) 
		MAX-ACCESS		read-write
		STATUS			current
		DESCRIPTION		"size  Description
1    speed (0=10, 1=100, 2=1000 Mbps )
1    duplex(0=Half,1=Full)
1    flowCtrlEnabled(1=Enabled, 0=Disabled)
1    autoNegEnabled(1=Enabled, 0=Disabled)
1    lenErrDiscard(1=Discard, 0=Allow)
1    enabled(1=Enabled, 0=Disabled)
1    linkUp(1=up,0=down)"
		::=  {  ucOnuPortUSREntry  5  }


	ucUSRPortRateCtrlIngress	OBJECT-TYPE	
		SYNTAX			DisplayString  ( SIZE ( 0 .. 128  ) ) 
		MAX-ACCESS		read-write
		STATUS			current
		DESCRIPTION		"size    Description
1  unit(0=Kbps,1=Mbps)----Default(0)
1  numRateLevels(num of OnuPolicerData)----Default(1)----Min(1)----Max(varies)
1       OnuPolicerData:
         u8_t trafficBits(Bit 0: Broadcast,Bit 1: Multicast,Bit 2: 802.1d reserved group (01:80:C2:00:00:0x),Bit 3: Unicast,Bit 4: Flooded unicast,Bits 5..7: Reserved for future use)
4       maxRate(Rate in terms of HxRateUnit)


When the ONU chip is connected to the Marvell 88E6095 or 88E6045 part, there are a few restrictions. The Marvell part only supports certain combination of traffic types when applying policing. Trying to set any unsupported combination will cause an error to be returned by the ONU.
The Marvell part does not support burst size configuration for rate limiting/shaping and consequently, setting this value has no effect on the ONU.
The rate settings are not settable with values from a linear scale. The Marvell part is programmed with a rate value that translates to (250000 / rate). In the firmware we cap the resulting value to 8-bits. This means that the rate can vary from 984 kbps to 250000 kbps (on a non-linear scale). Rates less than 984 are interpreted by the ONU as 984
kbps. Setting a zero rate disables shaping/policing.
Egress shaping cannot be done on the basis of traffic types (Unicast, Flooded Unicast, Multicast or Broadcast).
The provisioned values are not currently stored in NVS."
		::=  {  ucOnuPortUSREntry  6  }


	ucUSRPortRateCtrlEgress	OBJECT-TYPE	
		SYNTAX			DisplayString  ( SIZE ( 0 .. 128  ) ) 
		MAX-ACCESS		read-write
		STATUS			current
		DESCRIPTION		"Size    Description
1 Type of traffic to control (Bitmap)----Default(0)----Min(0)----Max(0xF) 
    Bit 0: Broadcast
    Bit 1: Multicast
    Bit 2: 802.1d reserved group (01:80:C2:00:00:0x)
    Bit 3: Unicast
    Bit 4: Flooded unicast
    Bits 5-7: Reserved for future use
1 Rate units (0 = Kbps, 1 = Frames/second)----Default(0)----Min(0)----Max(1) 
1 Number of Shapers----Default(1)----Min(1)----Max(varies) 
1     Queue Bitmap. Queues to which shaping applies.
4     Maximum rate
2     Burst size----Units(Kbytes)
1     Scheduling algorithm(may be a global
       setting, depending upon the hardware)----Default(0)----Min(0)----Max(1) 
       0: Weighted-fair
       1: Strict priority
1     Number of Weights (highest priority first)
1          Weight


When the ONU chip is connected to the Marvell 88E6095 or 88E6045 part, there are a few restrictions. The Marvell part only supports certain combination of traffic types
when applying policing. Trying to set any unsupported combination will cause an error to be returned by the ONU.
The Marvell part does not support burst size configuration for rate limiting/shaping and consequently, setting this value has no effect on the ONU.
The rate settings are not settable with values from a linear scale. The Marvell part is programmed with a rate value that translates to (250000 / rate). In the firmware we cap the resulting value to 8-bits. This means that the rate can vary from 984 kbps to 250000 kbps (on a non-linear scale). Rates less than 984 are interpreted by the ONU as 984
kbps. Setting a zero rate disables shaping/policing.
Egress shaping cannot be done on the basis of traffic types (Unicast, Flooded Unicast, Multicast or Broadcast).
The provisioned values are not currently stored in NVS."
		::=  {  ucOnuPortUSREntry  7  }


	ucUSRPortName	OBJECT-TYPE	
		SYNTAX			DisplayString  ( SIZE ( 0 .. 32  ) ) 
		MAX-ACCESS		read-write
		STATUS			current
		DESCRIPTION		"ucUSRPortName"
		::=  {  ucOnuPortUSREntry  8  }

-- ######################################################################
-- Add OLT Uplink Port Vlan Mib Branch !!!  
-- 2017.06.08

-- 2.6.1.3
    	ucOltUplinkPortVlanTable OBJECT-TYPE
    		SYNTAX SEQUENCE OF UcOltUplinkPortVlanEntry
    		MAX-ACCESS not-accessible
    		STATUS mandatory
    		DESCRIPTION "" 
    	::= { ucPonPort 3 }
    	
    	-- 2.6.1.3.1
    	ucOltUplinkPortVlanEntry OBJECT-TYPE    
    		SYNTAX UcOltUplinkPortVlanEntry
    		MAX-ACCESS not-accessible
    		STATUS mandatory
    		DESCRIPTION ""
    		INDEX { ucOltUplinkPortVlanSlotIndex,ucOltUplinkPortVlanPonIndex }
    	::= { ucOltUplinkPortVlanTable 1 }
    	
    	UcOltUplinkPortVlanEntry ::= SEQUENCE
    	{      
    		ucOltUplinkPortVlanSlotIndex		Integer32,
    		ucOltUplinkPortVlanPonIndex  		Integer32,
    		ucOltUplinkPortVlanTpid		      Integer32,
    		ucOltUplinkPortVlanId  		      Integer32
    	}
    	
   		ucOltUplinkPortVlanSlotIndex OBJECT-TYPE
   	 		SYNTAX  Integer32 (1..16)
     		MAX-ACCESS  read-only
     		STATUS current
     		DESCRIPTION ""
   		::= { ucOltUplinkPortVlanEntry 1 }
   		
   		ucOltUplinkPortVlanPonIndex OBJECT-TYPE
   	 		SYNTAX  Integer32 (1..32)
     		MAX-ACCESS  read-only
     		STATUS current
     		DESCRIPTION ""
   		::= { ucOltUplinkPortVlanEntry 2 }   
       	   
   		ucOltUplinkPortVlanTpid OBJECT-TYPE
   	 		SYNTAX  Integer32
     		MAX-ACCESS  read-write
     		STATUS current
     		DESCRIPTION ""
   		::= { ucOltUplinkPortVlanEntry 3 }
                      
   		ucOltUplinkPortVlanId OBJECT-TYPE
   	 		SYNTAX  Integer32 (0..4095)
     		MAX-ACCESS  read-write
     		STATUS current
     		DESCRIPTION "0=Disable Vlan"
   		::= { ucOltUplinkPortVlanEntry 4 }
   		
-- 2.6.1.4
    	ucPonPortEncryptionTable OBJECT-TYPE
    		SYNTAX SEQUENCE OF UcPonPortEncryptionEntry
    		MAX-ACCESS not-accessible
    		STATUS mandatory
    		DESCRIPTION "" 
    	::= { ucPonPort 4 }
    	
    	-- 2.6.1.4.1
    	ucPonPortEncryptionEntry OBJECT-TYPE    
    		SYNTAX UcPonPortEncryptionEntry
    		MAX-ACCESS not-accessible
    		STATUS mandatory
    		DESCRIPTION ""
    		INDEX { ucPonPortEncryptionSlotIndex,ucPonPortEncryptionPonIndex }
    	::= { ucPonPortEncryptionTable 1 }
    	
    	UcPonPortEncryptionEntry ::= SEQUENCE
    	{      
    		ucPonPortEncryptionSlotIndex		Integer32,
    		ucPonPortEncryptionPonIndex  		Integer32,
    		ucPonPortEncryptionMode		      Integer32,
    		ucPonPortEncryptionKeyTimeout   Integer32
    	}
    	
   		ucPonPortEncryptionSlotIndex OBJECT-TYPE
   	 		SYNTAX  Integer32 (1..16)
     		MAX-ACCESS  read-only
     		STATUS current
     		DESCRIPTION ""
   		::= { ucPonPortEncryptionEntry 1 }
   		
   		ucPonPortEncryptionPonIndex OBJECT-TYPE
   	 		SYNTAX  Integer32 (1..32)
     		MAX-ACCESS  read-only
     		STATUS current
     		DESCRIPTION ""
   		::= { ucPonPortEncryptionEntry 2 }   
       	   
   		ucPonPortEncryptionMode OBJECT-TYPE
   	 		SYNTAX  Integer32 { noneEncryption(0),ctcTripleChurning(2) } 
     		MAX-ACCESS  read-write
     		STATUS current
     		DESCRIPTION ""
   		::= { ucPonPortEncryptionEntry 3 }
                      
   		ucPonPortEncryptionKeyTimeout OBJECT-TYPE
   	 		SYNTAX  Integer32 (0..65535)
     		MAX-ACCESS  read-write
     		STATUS current
     		DESCRIPTION "0=Disable Vlan"
   		::= { ucPonPortEncryptionEntry 4 }
   		
-- 2.6.1.5
    	ucPonAttemptRegTable OBJECT-TYPE
    		SYNTAX SEQUENCE OF UcPonAttemptRegEntry
    		MAX-ACCESS not-accessible
    		STATUS mandatory
    		DESCRIPTION "" 
    	::= { ucPonPort 5 }
    	
    	-- 2.6.1.5.1
    	ucPonAttemptRegEntry OBJECT-TYPE    
    		SYNTAX UcPonAttemptRegEntry
    		MAX-ACCESS not-accessible
    		STATUS mandatory
    		DESCRIPTION ""
    		INDEX { ucPonAttemptRegSlotIndex,ucPonAttemptRegPonIndex,ucPonAttemptRegLinkIndex }
    	::= { ucPonAttemptRegTable 1 }
    	
    	UcPonAttemptRegEntry ::= SEQUENCE
    	{      
    		ucPonAttemptRegSlotIndex		Integer32,
    		ucPonAttemptRegPonIndex  		Integer32,
    		ucPonAttemptRegLinkIndex  	Integer32,
    		ucPonAttemptRegLinkMac		  OCTET STRING,
    		ucPonAttemptRegLinkOp   		Integer32
    	}
    	
   		ucPonAttemptRegSlotIndex OBJECT-TYPE
   	 		SYNTAX  Integer32 (1..16)
     		MAX-ACCESS  read-only
     		STATUS current
     		DESCRIPTION ""
   		::= { ucPonAttemptRegEntry 1 }
   		
   		ucPonAttemptRegPonIndex OBJECT-TYPE
   	 		SYNTAX  Integer32 (1..32)
     		MAX-ACCESS  read-only
     		STATUS current
     		DESCRIPTION ""
   		::= { ucPonAttemptRegEntry 2 }
   		
   		ucPonAttemptRegLinkIndex OBJECT-TYPE
   	 		SYNTAX  Integer32 (1..128)
     		MAX-ACCESS  read-only
     		STATUS current
     		DESCRIPTION ""
   		::= { ucPonAttemptRegEntry 3 }   
   		
   		ucPonAttemptRegLinkMac  OBJECT-TYPE  
		    SYNTAX			OCTET STRING (SIZE(6..6))
		    MAX-ACCESS		read-only
		    STATUS        mandatory
		    DESCRIPTION   "LLID MAC address" 
		  ::=  {  ucPonAttemptRegEntry  4 }
		       	   
   		ucPonAttemptRegLinkOp OBJECT-TYPE
   	 		SYNTAX  Integer32 { linkOp_none(0),linkOp_confirm(1) } 
     		MAX-ACCESS  read-write
     		STATUS current
     		DESCRIPTION ""
   		::= { ucPonAttemptRegEntry 5 }
   		
   		
   		   		
	ucOperaParaSLATable	OBJECT-TYPE
		SYNTAX		SEQUENCE  OF  UcOperaParaSLAEntry
		MAX-ACCESS	not-accessible
		STATUS		current
		DESCRIPTION	"Description"
		::=  { ucOperaPara  1 }

	ucOperaParaSLAEntry	OBJECT-TYPE
		SYNTAX		UcOperaParaSLAEntry
		MAX-ACCESS	not-accessible
		STATUS		current
		DESCRIPTION	"Description"
		INDEX		{  ucOperaParaSLASlotIndex, ucOperaParaSLAPonIndex, ucOperaParaSLAONUIndex, ucOperaParaSLALLIDIndex, ucOperaParaSLAType, ucOperaParaSLADirection  }
		::=  { ucOperaParaSLATable 1 }

	UcOperaParaSLAEntry  ::=  SEQUENCE {
		ucOperaParaSLASlotIndex  Integer32,
		ucOperaParaSLAPonIndex  Integer32,
		ucOperaParaSLAONUIndex  Integer32,
		ucOperaParaSLALLIDIndex  Integer32,
		ucOperaParaSLAType  INTEGER,
		ucOperaParaSLADirection  INTEGER,
		ucOperaParaSLAMaxBW  Integer32,
		ucOperaParaSLAMinBW  Integer32,
		ucOperaParaSLADelayMode  INTEGER,
		ucOperaParaSLAMaxBurstSize  Integer32,
		ucOperaParaSLATdmrate  Integer32,
		ucOperaParaSLATdmgrantlen  Integer32,
		ucOperaParaSLAStatus  INTEGER,
		ucOperaParaSLADBATokens  Integer32,
		ucOperaParaSLASchedMintokens  Integer32,
		ucOperaParaSLASchedMaxtokens  Integer32,
		ucOperaParaSLAForceReport  INTEGER,
		ucOperaParaSLALLID         OCTET STRING
		}


	ucOperaParaSLASlotIndex	OBJECT-TYPE	
		SYNTAX			Integer32  ( 1 .. 16  ) 
		MAX-ACCESS		read-only
		STATUS			current
		DESCRIPTION		"Description."
		::=  {  ucOperaParaSLAEntry  1  }


	ucOperaParaSLAPonIndex	OBJECT-TYPE	
		SYNTAX			Integer32  ( 1 .. 32  ) 
		MAX-ACCESS		read-only
		STATUS			current
		DESCRIPTION		"Description."
		::=  {  ucOperaParaSLAEntry  2  }


	ucOperaParaSLAONUIndex	OBJECT-TYPE	
		SYNTAX			Integer32  ( 1 .. 256  ) 
		MAX-ACCESS		read-only
		STATUS			current
		DESCRIPTION		"Description."
		::=  {  ucOperaParaSLAEntry  3  }


	ucOperaParaSLALLIDIndex	OBJECT-TYPE	
		SYNTAX			Integer32  ( 1 .. 32  ) 
		MAX-ACCESS		read-only
		STATUS			current
		DESCRIPTION		"Description."
		::=  {  ucOperaParaSLAEntry  4  }


	ucOperaParaSLAType	OBJECT-TYPE	
		SYNTAX			INTEGER  { unicast ( 1 ) , multicast ( 2 ) , broadcast ( 3 ) } 
		MAX-ACCESS		read-only
		STATUS			current
		DESCRIPTION		"Description."
		::=  {  ucOperaParaSLAEntry  5  }


	ucOperaParaSLADirection	OBJECT-TYPE	
		SYNTAX			INTEGER  { upstream ( 1 ) , downstream ( 2 ) } 
		MAX-ACCESS		read-only
		STATUS			current
		DESCRIPTION		"Description."
		::=  {  ucOperaParaSLAEntry  6  }


	ucOperaParaSLAMaxBW	OBJECT-TYPE	
		SYNTAX			Integer32  ( 0 .. 1000000  ) 
		MAX-ACCESS		read-write
		STATUS			current
		DESCRIPTION		"Description."
		::=  {  ucOperaParaSLAEntry  7  }


	ucOperaParaSLAMinBW	OBJECT-TYPE	
		SYNTAX			Integer32  ( 0 .. 1000000  ) 
		MAX-ACCESS		read-write
		STATUS			current
		DESCRIPTION		"Description."
		::=  {  ucOperaParaSLAEntry  8  }


	ucOperaParaSLADelayMode	OBJECT-TYPE	
		SYNTAX			INTEGER  { tolerant ( 0 ) , sensitive ( 1 ) , tdm ( 2 ) } 
		MAX-ACCESS		read-write
		STATUS			current
		DESCRIPTION		"Description."
		::=  {  ucOperaParaSLAEntry  9  }


	ucOperaParaSLAMaxBurstSize	OBJECT-TYPE	
		SYNTAX			Integer32  ( 1 .. 256  ) 
		MAX-ACCESS		read-write
		STATUS			current
		DESCRIPTION		"Description."
		::=  {  ucOperaParaSLAEntry  10  }


	ucOperaParaSLATdmrate	OBJECT-TYPE	
		SYNTAX			Integer32  ( 0 .. 4000  ) 
		MAX-ACCESS		read-write
		STATUS			current
		DESCRIPTION		"Description."
		::=  {  ucOperaParaSLAEntry  11  }


	ucOperaParaSLATdmgrantlen	OBJECT-TYPE	
		SYNTAX			Integer32  ( 0 .. 131072  ) 
		MAX-ACCESS		read-write
		STATUS			current
		DESCRIPTION		"Description."
		::=  {  ucOperaParaSLAEntry  12  }


	ucOperaParaSLAStatus	OBJECT-TYPE	
		SYNTAX			INTEGER  { disabled ( 1 ) , enabled ( 2 ) , delete ( 3 ) } 
		MAX-ACCESS		read-write
		STATUS			current
		DESCRIPTION		"Description."
		::=  {  ucOperaParaSLAEntry  13  }


	ucOperaParaSLADBATokens	OBJECT-TYPE	
		SYNTAX			Integer32  ( 0 .. 255  ) 
		MAX-ACCESS		read-write
		STATUS			current
		DESCRIPTION		"Description."
		::=  {  ucOperaParaSLAEntry  14  }


	ucOperaParaSLASchedMintokens	OBJECT-TYPE	
		SYNTAX			Integer32  ( 0 .. 511  ) 
		MAX-ACCESS		read-write
		STATUS			current
		DESCRIPTION		"Description."
		::=  {  ucOperaParaSLAEntry  15  }


	ucOperaParaSLASchedMaxtokens	OBJECT-TYPE	
		SYNTAX			Integer32  ( 0 .. 511  ) 
		MAX-ACCESS		read-write
		STATUS			current
		DESCRIPTION		"Description."
		::=  {  ucOperaParaSLAEntry  16  }


	ucOperaParaSLAForceReport	OBJECT-TYPE	
		SYNTAX			INTEGER  { false ( 0 ) , true ( 1 ) } 
		MAX-ACCESS		read-write
		STATUS			current
		DESCRIPTION		"Description."
		::=  {  ucOperaParaSLAEntry  17  }
	
	ucOperaParaSLALLID  OBJECT-TYPE  
		SYNTAX			OCTET STRING (SIZE(6..6))
		MAX-ACCESS		read-only
		STATUS          mandatory
		DESCRIPTION     "LLID MAC address" 
		::=  {  ucOperaParaSLAEntry  18  }
		
	

	ucOLTBwTable	OBJECT-TYPE
		SYNTAX		SEQUENCE  OF  UcOLTBwEntry
		MAX-ACCESS	not-accessible
		STATUS		current
		DESCRIPTION	"Description"
		::=  { ucOperaPara  2 }

	ucOLTBwEntry	OBJECT-TYPE
		SYNTAX		UcOLTBwEntry
		MAX-ACCESS	not-accessible
		STATUS		current
		DESCRIPTION	"Description"
		INDEX		{  ucOLTBwSlotIndex, ucOLTBwPonIndex, ucOLTBwDir  }
		::=  { ucOLTBwTable 1 }

	UcOLTBwEntry  ::=  SEQUENCE {
		ucOLTBwSlotIndex  Integer32,
		ucOLTBwPonIndex  Integer32,
		ucOLTBwDir  INTEGER,
		ucOLTBwAggretateBw  Integer32,
		ucOLTBwMaxBurstSize  Integer32
		}


	ucOLTBwSlotIndex	OBJECT-TYPE	
		SYNTAX			Integer32  ( 1 .. 16  ) 
		MAX-ACCESS		read-only
		STATUS			current
		DESCRIPTION		"Description."
		::=  {  ucOLTBwEntry  1  }


	ucOLTBwPonIndex	OBJECT-TYPE	
		SYNTAX			Integer32  ( 1 .. 32  ) 
		MAX-ACCESS		read-only
		STATUS			current
		DESCRIPTION		"Description."
		::=  {  ucOLTBwEntry  2  }


	ucOLTBwDir	OBJECT-TYPE	
		SYNTAX			INTEGER  { downstream ( 1 ) , upstream ( 2 ) } 
		MAX-ACCESS		read-only
		STATUS			current
		DESCRIPTION		"Description."
		::=  {  ucOLTBwEntry  3  }


	ucOLTBwAggretateBw	OBJECT-TYPE	
		SYNTAX			Integer32  ( 0 .. 1000000  ) 
		MAX-ACCESS		read-write
		STATUS			current
		DESCRIPTION		"Description."
		::=  {  ucOLTBwEntry  4  }


	ucOLTBwMaxBurstSize	OBJECT-TYPE	
		SYNTAX			Integer32  ( 0 .. 256  ) 
		MAX-ACCESS		read-write
		STATUS			current
		DESCRIPTION		"Description."
		::=  {  ucOLTBwEntry  5  }

	ucPortFramePrioMapTable	OBJECT-TYPE
		SYNTAX		SEQUENCE  OF  UcPortFramePrioMapEntry
		MAX-ACCESS	not-accessible
		STATUS		current
		DESCRIPTION	"Description"
		::=  { ucOperaPara  3 }

	ucPortFramePrioMapEntry	OBJECT-TYPE
		SYNTAX		UcPortFramePrioMapEntry
		MAX-ACCESS	not-accessible
		STATUS		current
		DESCRIPTION	"Description"
		INDEX		{  ucPrioMapSlotIndex, ucPrioMapPonIndex, ucPrioMapOnuIndex, ucPrioMapPortIndex  }
		::=  { ucPortFramePrioMapTable 1 }

	UcPortFramePrioMapEntry  ::=  SEQUENCE {
		ucPrioMapSlotIndex  Integer32,
		ucPrioMapPonIndex  Integer32,
		ucPrioMapOnuIndex  Integer32,
		ucPrioMapPortIndex  Integer32,
		ucPrioMapEnqueuingMap  DisplayString
		}


	ucPrioMapSlotIndex	OBJECT-TYPE	
		SYNTAX			Integer32  ( 1 .. 16  ) 
		MAX-ACCESS		read-only
		STATUS			current
		DESCRIPTION		"Description."
		::=  {  ucPortFramePrioMapEntry  1  }


	ucPrioMapPonIndex	OBJECT-TYPE	
		SYNTAX			Integer32  ( 1 .. 32  ) 
		MAX-ACCESS		read-only
		STATUS			current
		DESCRIPTION		"Description."
		::=  {  ucPortFramePrioMapEntry  2  }


	ucPrioMapOnuIndex	OBJECT-TYPE	
		SYNTAX			Integer32  ( 1 .. 256  ) 
		MAX-ACCESS		read-only
		STATUS			current
		DESCRIPTION		"Description."
		::=  {  ucPortFramePrioMapEntry  3  }


	ucPrioMapPortIndex	OBJECT-TYPE	
		SYNTAX			Integer32  ( 1 .. 24  ) 
		MAX-ACCESS		read-only
		STATUS			current
		DESCRIPTION		"Description."
		::=  {  ucPortFramePrioMapEntry  4  }


	ucPrioMapEnqueuingMap	OBJECT-TYPE	
		SYNTAX			DisplayString  ( SIZE ( 3 .. 24738  ) ) 
		MAX-ACCESS		read-only
		STATUS			current
		DESCRIPTION		"Description."
		::=  {  ucPortFramePrioMapEntry  5  }

	ucPortCosTable	OBJECT-TYPE
		SYNTAX		SEQUENCE  OF  UcPortCosEntry
		MAX-ACCESS	not-accessible
		STATUS		current
		DESCRIPTION	"Description"
		::=  { ucOperaPara  4 }

	ucPortCosEntry	OBJECT-TYPE
		SYNTAX		UcPortCosEntry
		MAX-ACCESS	not-accessible
		STATUS		current
		DESCRIPTION	"Description"
		INDEX		{  ucPortCosSlotIndex, ucPortCosPonIndex, ucPortCosOnuIndex, ucPortCosPortIndex  }
		::=  { ucPortCosTable 1 }

	UcPortCosEntry  ::=  SEQUENCE {
		ucPortCosSlotIndex  Integer32,
		ucPortCosPonIndex  Integer32,
		ucPortCosOnuIndex  Integer32,
		ucPortCosPortIndex  Integer32,
		ucPortCosCtrl  DisplayString
		}


	ucPortCosSlotIndex	OBJECT-TYPE	
		SYNTAX			Integer32  ( 1 .. 16  ) 
		MAX-ACCESS		read-only
		STATUS			current
		DESCRIPTION		"Description."
		::=  {  ucPortCosEntry  1  }


	ucPortCosPonIndex	OBJECT-TYPE	
		SYNTAX			Integer32  ( 1 .. 32  ) 
		MAX-ACCESS		read-only
		STATUS			current
		DESCRIPTION		"Description."
		::=  {  ucPortCosEntry  2  }


	ucPortCosOnuIndex	OBJECT-TYPE	
		SYNTAX			Integer32  ( 1 .. 256  ) 
		MAX-ACCESS		read-only
		STATUS			current
		DESCRIPTION		"Description."
		::=  {  ucPortCosEntry  3  }


	ucPortCosPortIndex	OBJECT-TYPE	
		SYNTAX			Integer32  ( 1 .. 24  ) 
		MAX-ACCESS		read-only
		STATUS			current
		DESCRIPTION		"Description."
		::=  {  ucPortCosEntry  4  }


	ucPortCosCtrl	OBJECT-TYPE	
		SYNTAX			DisplayString  ( SIZE ( 0 .. 255  ) ) 
		MAX-ACCESS		read-write
		STATUS			current
		DESCRIPTION		"Size    Description
1 Input Priority options (bitmap)
1 Number of priority mapping tables
1     Input Priority Type (COS=0, TOS=1,DiffServ/Traffic Class=2)
1     Minimum priority for output COS 0
1     Maximum priority for output COS 0
       &
1     Minimum priority for output COS 7
1     Maximum priority for output COS 7


When the ONU chip is connected to the Marvell 88E6095 or 88E6045 part, there are restrictions. The Marvell chip can only translate CoS priorities on tags that are generated inside the chip. The part does not recognize tags in incoming frames and apply CoS translation rules on it. It will only apply the translation to tags that the chip generates internally. Essentially, to have a semblance of this feature in action, the OLT needs to be prepared to receive frames with one extra VLAN tag added to frames input into the ONU. The translated CoS is available in the outermost VLAN tag."
		::=  {  ucPortCosEntry  5  }

	ucOperaParaOltBroadcastSLATable	OBJECT-TYPE
		SYNTAX		SEQUENCE  OF  UcOperaParaOltBroadcastSLAEntry
		MAX-ACCESS	not-accessible
		STATUS		current
		DESCRIPTION	"Description"
		::=  { ucOperaPara  5 }

	ucOperaParaOltBroadcastSLAEntry	OBJECT-TYPE
		SYNTAX		UcOperaParaOltBroadcastSLAEntry
		MAX-ACCESS	not-accessible
		STATUS		current
		DESCRIPTION	"Description"
		INDEX		{  ucOperaParaBrdSLASlotIndex, ucOperaParaBrdSLAPonIndex, ucOperaParaBrdSLADirection  }
		::=  { ucOperaParaOltBroadcastSLATable 1 }

	UcOperaParaOltBroadcastSLAEntry  ::=  SEQUENCE {
		ucOperaParaBrdSLASlotIndex  Integer32,
		ucOperaParaBrdSLAPonIndex  Integer32,
		ucOperaParaBrdSLADirection  INTEGER,
		ucOperaParaBrdSLAMaxBW  Integer32,
		ucOperaParaBrdSLAMinBW  Integer32,
		ucOperaParaBrdSLADelayMode  INTEGER,
		ucOperaParaBrdSLAMaxBurstSize  Integer32,
		ucOperaParaBrdSLAStatus  INTEGER,
		ucOperaParaBrdSLASchedMintokens  Integer32,
		ucOperaParaBrdSLASchedMaxtokens  Integer32
		}


	ucOperaParaBrdSLASlotIndex	OBJECT-TYPE	
		SYNTAX			Integer32  ( 1 .. 16  ) 
		MAX-ACCESS		read-only
		STATUS			current
		DESCRIPTION		"Description."
		::=  {  ucOperaParaOltBroadcastSLAEntry  1  }


	ucOperaParaBrdSLAPonIndex	OBJECT-TYPE	
		SYNTAX			Integer32  ( 1 .. 32  ) 
		MAX-ACCESS		read-only
		STATUS			current
		DESCRIPTION		"Description."
		::=  {  ucOperaParaOltBroadcastSLAEntry  2  }


	ucOperaParaBrdSLADirection	OBJECT-TYPE	
		SYNTAX			INTEGER  { upstream ( 1 ) , downstream ( 2 ) } 
		MAX-ACCESS		read-only
		STATUS			current
		DESCRIPTION		"Description."
		::=  {  ucOperaParaOltBroadcastSLAEntry  3  }


	ucOperaParaBrdSLAMaxBW	OBJECT-TYPE	
		SYNTAX			Integer32  ( 0 .. 1000000  ) 
		MAX-ACCESS		read-write
		STATUS			current
		DESCRIPTION		"Description."
		::=  {  ucOperaParaOltBroadcastSLAEntry  4  }


	ucOperaParaBrdSLAMinBW	OBJECT-TYPE	
		SYNTAX			Integer32  ( 0 .. 1000000  ) 
		MAX-ACCESS		read-write
		STATUS			current
		DESCRIPTION		"Description."
		::=  {  ucOperaParaOltBroadcastSLAEntry  5  }


	ucOperaParaBrdSLADelayMode	OBJECT-TYPE	
		SYNTAX			INTEGER  { tolerant ( 0 ) , sensitive ( 1 ) , tdm ( 2 ) } 
		MAX-ACCESS		read-write
		STATUS			current
		DESCRIPTION		"Description."
		::=  {  ucOperaParaOltBroadcastSLAEntry  6  }


	ucOperaParaBrdSLAMaxBurstSize	OBJECT-TYPE	
		SYNTAX			Integer32  ( 1 .. 256  ) 
		MAX-ACCESS		read-write
		STATUS			current
		DESCRIPTION		"Description."
		::=  {  ucOperaParaOltBroadcastSLAEntry  7  }


	ucOperaParaBrdSLAStatus	OBJECT-TYPE	
		SYNTAX			INTEGER  { disabled ( 1 ) , enabled ( 2 ) , delete ( 3 ) } 
		MAX-ACCESS		read-write
		STATUS			current
		DESCRIPTION		"Description."
		::=  {  ucOperaParaOltBroadcastSLAEntry  8  }


	ucOperaParaBrdSLASchedMintokens	OBJECT-TYPE	
		SYNTAX			Integer32  ( 0 .. 511  ) 
		MAX-ACCESS		read-write
		STATUS			current
		DESCRIPTION		"Description."
		::=  {  ucOperaParaOltBroadcastSLAEntry  9  }


	ucOperaParaBrdSLASchedMaxtokens	OBJECT-TYPE	
		SYNTAX			Integer32  ( 0 .. 511  ) 
		MAX-ACCESS		read-write
		STATUS			current
		DESCRIPTION		"Description."
		::=  {  ucOperaParaOltBroadcastSLAEntry  10  }

	ucCfgOLTTable	OBJECT-TYPE
		SYNTAX		SEQUENCE  OF  UcCfgOLTEntry
		MAX-ACCESS	not-accessible
		STATUS		current
		DESCRIPTION	"Description"
		::=  { ucBoardCfg  1 }

	ucCfgOLTEntry	OBJECT-TYPE
		SYNTAX		UcCfgOLTEntry
		MAX-ACCESS	not-accessible
		STATUS		current
		DESCRIPTION	"Description"
		INDEX		{  ucCfgOLTSlotIndex  }
		::=  { ucCfgOLTTable 1 }

	UcCfgOLTEntry  ::=  SEQUENCE {
		ucCfgOLTSlotIndex  Integer32,
		ucCfgOLTType  DisplayString,
		ucCfgOLTHostIP  IpAddress,
		ucCfgOLTHostUdpPort  Integer32,
		ucCfgOLTIp  IpAddress,
		ucCfgOLTUdpPort  Integer32,
		ucCfgOLTCTC  INTEGER,
		ucCfgOLTCTCOUI  DisplayString,
		ucCfgOLTNumLinks  Integer32,
		ucCfgOLTIEEEOUI  DisplayString,
		ucCfgOLTProductVersion  DisplayString,
		ucCfgOLTFirmwareVersion  DisplayString,
		ucCfgOLTVendorInfo  OCTET STRING,
		ucCfgOLTChipID  DisplayString,
		ucCfgOLTChipVersion  DisplayString,
		ucCfgOLTBootVersion  DisplayString,
		ucCfgOLTPersonalityV  DisplayString,
		ucCfgOLTApp0Version  DisplayString,
		ucCfgOLTApp1Version  DisplayString,
		ucCfgOLTDiagVersion  DisplayString,
		uCCfgOLTNvsEnabled  INTEGER,
		ucCfgOLTMac  OCTET STRING,
		ucCfgOLTOnuAuthenMode  INTEGER,
		ucCfgOLTName  OCTET STRING,
		ucCfgOLTLNPName  OCTET STRING,
		ucSLABroadcastCtrl  DisplayString,
		ucSLAWeightBroadcastCtrl  DisplayString,
		ucAggregateBandwidthDownStream  DisplayString,
		ucAggregateBandwidthUpstream  DisplayString,
		ucCfgOLTOperation  DisplayString,
		ucCfgOLTONUs  DisplayString,
		ucCfgOLTLLIDs  DisplayString,
		ucCfgOLTONU2ONU Integer32,
		ucCfgOLTQinQTpid Integer32,
		ucCfgOLTQinQVlan Integer32,
		ucCfgOLTCtcDisable Integer32,
		ucCfgOLTIgmpProxy Integer32,
		ucCfgOLTMtu Integer32,
		ucCfgOLTNniIsolation Integer32
		}


	ucCfgOLTSlotIndex	OBJECT-TYPE	
		SYNTAX			Integer32  ( 1 .. 16  ) 
		MAX-ACCESS		read-only
		STATUS			current
		DESCRIPTION		"Description."
		::=  {  ucCfgOLTEntry  1  }


	ucCfgOLTType	OBJECT-TYPE	
		SYNTAX			DisplayString  ( SIZE ( 4 .. 4  ) ) 
		MAX-ACCESS		read-only
		STATUS			current
		DESCRIPTION		"Description."
		::=  {  ucCfgOLTEntry  2  }


	ucCfgOLTHostIP	OBJECT-TYPE	
		SYNTAX			IpAddress
		MAX-ACCESS		read-write
		STATUS			current
		DESCRIPTION		"Description."
		::=  {  ucCfgOLTEntry  3  }


	ucCfgOLTHostUdpPort	OBJECT-TYPE	
		SYNTAX			Integer32  ( 1 .. 65535  ) 
		MAX-ACCESS		read-write
		STATUS			current
		DESCRIPTION		"Description."
		::=  {  ucCfgOLTEntry  4  }


	ucCfgOLTIp	OBJECT-TYPE	
		SYNTAX			IpAddress
		MAX-ACCESS		read-write
		STATUS			current
		DESCRIPTION		"Description."
		::=  {  ucCfgOLTEntry  5  }


	ucCfgOLTUdpPort	OBJECT-TYPE	
		SYNTAX			Integer32  ( 1 .. 65535  ) 
		MAX-ACCESS		read-write
		STATUS			current
		DESCRIPTION		"Description."
		::=  {  ucCfgOLTEntry  6  }


	ucCfgOLTCTC	OBJECT-TYPE	
		SYNTAX			INTEGER  { enable ( 1 ) , disable ( 2 ) } 
		MAX-ACCESS		read-only
		STATUS			current
		DESCRIPTION		"Description."
		::=  {  ucCfgOLTEntry  7  }


	ucCfgOLTCTCOUI	OBJECT-TYPE	
		SYNTAX			DisplayString  ( SIZE ( 6 .. 6  ) ) 
		MAX-ACCESS		read-only
		STATUS			current
		DESCRIPTION		"Description."
		::=  {  ucCfgOLTEntry  8  }


	ucCfgOLTNumLinks	OBJECT-TYPE	
		SYNTAX			Integer32  ( 0 .. 239  ) 
		MAX-ACCESS		read-only
		STATUS			current
		DESCRIPTION		"Description."
		::=  {  ucCfgOLTEntry  9  }


	ucCfgOLTIEEEOUI	OBJECT-TYPE	
		SYNTAX			DisplayString  ( SIZE ( 6 .. 6  ) ) 
		MAX-ACCESS		read-only
		STATUS			current
		DESCRIPTION		"Description."
		::=  {  ucCfgOLTEntry  10  }


	ucCfgOLTProductVersion	OBJECT-TYPE	
		SYNTAX			DisplayString  ( SIZE ( 4 .. 4  ) ) 
		MAX-ACCESS		read-only
		STATUS			current
		DESCRIPTION		"Description."
		::=  {  ucCfgOLTEntry  11  }


	ucCfgOLTFirmwareVersion	OBJECT-TYPE	
		SYNTAX			DisplayString  ( SIZE ( 4 .. 4  ) ) 
		MAX-ACCESS		read-only
		STATUS			current
		DESCRIPTION		"Description."
		::=  {  ucCfgOLTEntry  12  }


	ucCfgOLTVendorInfo	OBJECT-TYPE	
		SYNTAX			OCTET STRING  ( SIZE ( 64 .. 64  ) ) 
		MAX-ACCESS		read-only
		STATUS			current
		DESCRIPTION		"Description."
		::=  {  ucCfgOLTEntry  13  }


	ucCfgOLTChipID	OBJECT-TYPE	
		SYNTAX			DisplayString  ( SIZE ( 4 .. 4  ) ) 
		MAX-ACCESS		read-only
		STATUS			current
		DESCRIPTION		"Description."
		::=  {  ucCfgOLTEntry  14  }


	ucCfgOLTChipVersion	OBJECT-TYPE	
		SYNTAX			DisplayString  ( SIZE ( 8 .. 8  ) ) 
		MAX-ACCESS		read-only
		STATUS			current
		DESCRIPTION		"Description."
		::=  {  ucCfgOLTEntry  15  }


	ucCfgOLTBootVersion	OBJECT-TYPE	
		SYNTAX			DisplayString  ( SIZE ( 4 .. 4  ) ) 
		MAX-ACCESS		read-only
		STATUS			current
		DESCRIPTION		"Description."
		::=  {  ucCfgOLTEntry  16  }


	ucCfgOLTPersonalityV	OBJECT-TYPE	
		SYNTAX			DisplayString  ( SIZE ( 4 .. 4  ) ) 
		MAX-ACCESS		read-only
		STATUS			current
		DESCRIPTION		"Description."
		::=  {  ucCfgOLTEntry  17  }


	ucCfgOLTApp0Version	OBJECT-TYPE	
		SYNTAX			DisplayString  ( SIZE ( 4 .. 4  ) ) 
		MAX-ACCESS		read-only
		STATUS			current
		DESCRIPTION		"Description."
		::=  {  ucCfgOLTEntry  18  }


	ucCfgOLTApp1Version	OBJECT-TYPE	
		SYNTAX			DisplayString  ( SIZE ( 4 .. 4  ) ) 
		MAX-ACCESS		read-only
		STATUS			current
		DESCRIPTION		"Description."
		::=  {  ucCfgOLTEntry  19  }


	ucCfgOLTDiagVersion	OBJECT-TYPE	
		SYNTAX			DisplayString  ( SIZE ( 4 .. 4  ) ) 
		MAX-ACCESS		read-only
		STATUS			current
		DESCRIPTION		"Description."
		::=  {  ucCfgOLTEntry  20  }


	uCCfgOLTNvsEnabled	OBJECT-TYPE	
		SYNTAX			INTEGER  { disabled ( 1 ) , enabled ( 2 ) } 
		MAX-ACCESS		read-write
		STATUS			current
		DESCRIPTION		"Description."
		::=  {  ucCfgOLTEntry  21  }


	ucCfgOLTMac	OBJECT-TYPE	
		SYNTAX			OCTET STRING  ( SIZE ( 6 .. 6  ) ) 
		MAX-ACCESS		read-only
		STATUS			current
		DESCRIPTION		"Description."
		::=  {  ucCfgOLTEntry  22  }


	ucCfgOLTOnuAuthenMode	OBJECT-TYPE	
		SYNTAX			INTEGER  { accesson ( 1 ) , mac ( 2 ) , sn ( 3 ) } 
		MAX-ACCESS		read-write
		STATUS			current
		DESCRIPTION		"Description."
		::=  {  ucCfgOLTEntry  23  }


	ucCfgOLTName	OBJECT-TYPE	
		SYNTAX			OCTET STRING  ( SIZE ( 0 .. 32  ) ) 
		MAX-ACCESS		read-write
		STATUS			current
		DESCRIPTION		"Description."
		::=  {  ucCfgOLTEntry  24  }


	ucCfgOLTLNPName	OBJECT-TYPE	
		SYNTAX			OCTET STRING  ( SIZE ( 0 .. 32  ) ) 
		MAX-ACCESS		read-write
		STATUS			current
		DESCRIPTION		"Description."
		::=  {  ucCfgOLTEntry  25  }


	ucSLABroadcastCtrl	OBJECT-TYPE	
		SYNTAX			DisplayString  ( SIZE ( 0 .. 255  ) ) 
		MAX-ACCESS		read-write
		STATUS			current
		DESCRIPTION		"Size    Description
10 Queue Label(6:mac,2:port,2:queueNum)
1 Direction (1 =Downstream, 0 =Upstream)
4 Minimum Guaranteed Bandwidth ----Units(Kbps)--Default(100,000)--Min(256)--Max(1,000,000)
4 Maximum Allowed Bandwidth ----Units(Kbps)--Default(100,000)--Min(256(0 = Best Effort))--Max(1,000,000)
2 Delay Sensitive(0: Tolerant,1: Sensitive)----Default(0)
2 Max Burst Size ----Units(KBytes)--Default(100)--Min(1)--Max(256)
4 TDM Rate 250 ----Units(us)--Default(0)--Min(1)--Max(4000)
4 TDM Grant Length ----Units(Byte)--Default(0)--Min(84)--Max(131072)
2 Reserved 0
1 SLA State (Enabled = 1,Disabled = 0). This is included only in the Get SLA reply.


Note that hardware limits the accuracy of these values. Provisioned values will be rounded up by the firmware to
the next larger physically available increment. In addition, an additional 200 ppm may be added by the firmware
to the provisioned bandwidth to allow for permissible clock frequency differences between ONU and OLT. With
the TK3721, shaping is accurate to within 1% of the provisioned bandwidth values, and the maximum burst
allowed is accurate to within 5% of the maximum size. The minimum non-zero value that can be provisioned for
bandwidth values is 256Kbps. In addition, when setting an SLA where the Max Allowed BW > Min Guaranteed
BW, the difference must be 256Kbps or greater."
		::=  {  ucCfgOLTEntry  26  }


	ucSLAWeightBroadcastCtrl	OBJECT-TYPE	
		SYNTAX			DisplayString
		MAX-ACCESS		read-write
		STATUS			current
		DESCRIPTION		"Size    Description
10 Logical Link Label
1 Direction:(1 = Downstream, 0 = Upstream)
2 DBA Tokens (set to zero to restore defaults) ----Units(Kbytes)--Default(4)--Min(0)--Max(255)
2 Scheduler Min-tokens (set to zero to restore defaults) ----Units(Kbytes)--Default(2)--Min(0)--Max(511)
2 Scheduler Max-tokens (set to zero to restore defaults)----Units(Kbytes)--Default(2)--Min(0)--Max(511)


The link and queue schedulers in the TK3721 use a weighted priority-based round-robin discipline. In general the
appropriate values of priority and weight for a link are selected by the firmware when an SLA is specified. This
command provides a low-level control for setting the upstream and downstream weights on a per-link basis. It is
recommended that the Host use the default settings as far as possible."
		::=  {  ucCfgOLTEntry  27  }


	ucAggregateBandwidthDownStream	OBJECT-TYPE	
		SYNTAX			DisplayString  ( SIZE ( 0 .. 255  ) ) 
		MAX-ACCESS		read-write
		STATUS			current
		DESCRIPTION		"Size    Description
1 Direction (1 = Downstream, 0 =Upstream)
4 Aggregate (overall) Bandwidth ----Units(Kbps)--Default( 0)--Min( 0)--Max( 1,000,000)
2 Max Burst Size ----Units(KBytes)--Default( 0)--Min( 1)--Max( 256)


This command lets the Host place a limit on the overall bandwidth the OLT will allow for user traffic in each
direction. The individual per-link SLAs carve out appropriate share of the bandwidth from this overall maximum.
Aggregate bandwidth control can be disabled by setting the parameters to zero; the feature is disabled by default."
		::=  {  ucCfgOLTEntry  28  }


	ucAggregateBandwidthUpstream	OBJECT-TYPE	
		SYNTAX			DisplayString  ( SIZE ( 0 .. 255  ) ) 
		MAX-ACCESS		read-write
		STATUS			current
		DESCRIPTION		"Size    Description
1 Direction (1 = Downstream, 0 =Upstream)
4 Aggregate (overall) Bandwidth ----Units(Kbps)--Default( 0)--Min( 0)--Max( 1,000,000)
2 Max Burst Size ----Units(KBytes)--Default( 0)--Min( 1)--Max( 256)


This command lets the Host place a limit on the overall bandwidth the OLT will allow for user traffic in each
direction. The individual per-link SLAs carve out appropriate share of the bandwidth from this overall maximum.
Aggregate bandwidth control can be disabled by setting the parameters to zero; the feature is disabled by default."
		::=  {  ucCfgOLTEntry  29  }


	ucCfgOLTOperation	OBJECT-TYPE	
		SYNTAX			DisplayString  ( SIZE ( 0 .. 255  ) ) 
		MAX-ACCESS		read-write
		STATUS			current
		DESCRIPTION		"Size    Description
1 Operation(0=Nop,1=Add onu,2=Delete onu)
1 Number of Onu
6     Onu Mac Address"
		::=  {  ucCfgOLTEntry  30  }


	ucCfgOLTONUs	OBJECT-TYPE	
		SYNTAX			DisplayString  ( SIZE ( 0 .. 255  ) ) 
		MAX-ACCESS		read-only
		STATUS			current
		DESCRIPTION		"Size    Description
1 Number of Onu
1     Onu Index
6     MAC Address
2     Product Version
1     State
1     Ports
2     RTT
1     MaxLinks
1     AuthenMode
32    Name
64    SN"
		::=  {  ucCfgOLTEntry  31  }


	ucCfgOLTLLIDs	OBJECT-TYPE	
		SYNTAX			DisplayString  ( SIZE ( 0 .. 255  ) ) 
		MAX-ACCESS		read-only
		STATUS			current
		DESCRIPTION		"Size    Description
2 Number of LLIDs
1     Onu Index
2     LLID Index
1     LLID State
32    LLID Name"
		::=  {  ucCfgOLTEntry  32  }
		
	ucCfgOLTONU2ONU	OBJECT-TYPE	
		SYNTAX			Integer32  {disable(0),enable(1)}
		MAX-ACCESS		read-write
		STATUS			current
		DESCRIPTION		"For TK3723, indicates whether ONUs under the same PON can communicate to each other"
		::=  {  ucCfgOLTEntry  33  }  
				
	ucCfgOLTQinQTpid	OBJECT-TYPE	
		SYNTAX			Integer32  (1 .. 65535)
		MAX-ACCESS		read-write
		STATUS			current
		DESCRIPTION		"For TK3723,Set OLT QinQ TPID"
		::=  {  ucCfgOLTEntry  34  }
						             
	ucCfgOLTQinQVlan	OBJECT-TYPE	
		SYNTAX			Integer32  (0 .. 4095)
		MAX-ACCESS		read-write
		STATUS			current
		DESCRIPTION		"For TK3723,Set OLT QinQ VLAN ID"
		::=  {  ucCfgOLTEntry  35  }			
		
	ucCfgOLTCtcDisable	OBJECT-TYPE	
		SYNTAX			Integer32  {enableCtc(0),disableCtc(1)}
		MAX-ACCESS		read-write
		STATUS			current
		DESCRIPTION		"For TK3721,Set OLT Ctc OAM Disable"
		::=  {  ucCfgOLTEntry  36  }	
		
	ucCfgOLTIgmpProxy	OBJECT-TYPE	
		SYNTAX			Integer32  {enableProxy(0),disableProxy(1)}
		MAX-ACCESS		read-write
		STATUS			current
		DESCRIPTION		"For TK3721,Set OLT IGMP Proxy Disable"
		::=  {  ucCfgOLTEntry  37  }					
             
  ucCfgOLTMtu OBJECT-TYPE
		SYNTAX			Integer32  (1536 .. 1900)
		MAX-ACCESS		read-write
		STATUS			current
		DESCRIPTION		"Config OLT MTU value"
		::=  {  ucCfgOLTEntry  38  }
		
	ucCfgOLTNniIsolation OBJECT-TYPE
	  SYNTAX			Integer32  {disable(0),enable(1)}
		MAX-ACCESS		read-write
		STATUS			current
		DESCRIPTION		"Config OLT NNI Isolation"
		::=  {  ucCfgOLTEntry  39  }
-------------------------------------------------------------------------------------------------------------		

	ucCfgONUTable	OBJECT-TYPE
		SYNTAX		SEQUENCE  OF  UcCfgONUEntry
		MAX-ACCESS	not-accessible
		STATUS		current
		DESCRIPTION	"Description"
		::=  { ucBoardCfg  2 }

	ucCfgONUEntry	OBJECT-TYPE
		SYNTAX		UcCfgONUEntry
		MAX-ACCESS	not-accessible
		STATUS		current
		DESCRIPTION	"Description"
		INDEX		{  ucCfgONUSlotIndex, ucCfgONUPonIndex, ucCfgONUIndex  }
		::=  { ucCfgONUTable 1 }

	UcCfgONUEntry  ::=  SEQUENCE {
		ucCfgONUSlotIndex  Integer32,
		ucCfgONUPonIndex  Integer32,
		ucCfgONUIndex  Integer32,
		ucCfgONUIeeeOui  DisplayString,
		ucCfgONUProductCode  DisplayString,
		ucCfgONUProductVersion  DisplayString,
		ucCfgONULLIDAssigned  Integer32,
		ucCfgONUTKExtension  Integer32,
		ucCfgONUFirmwareVersion  DisplayString,
		ucCfgONUVendorInfo  OCTET STRING,
		ucCfgONUPhysicalID  DisplayString,
		ucCfgONUMaxLinks  Integer32,
		ucCfgONUPorts  Integer32,
		ucCfgONUChipJedec  DisplayString,
		ucCfgONUChipID  DisplayString,
		ucCfgONUChipVersion  DisplayString,
		ucCfgONUBootVersion  DisplayString,
		ucCfgONUPersVersion  DisplayString,
		ucCfgONUApp0Version  DisplayString,
		ucCfgONUApp1Version  DisplayString,
		ucCfgONUDiagVersion  DisplayString,
		ucCfgONUReset  INTEGER,
		ucCfgONURestoreDefault  INTEGER,
		ucCfgONUUserTraffic  INTEGER,
		ucCfgONURTT  Integer32,
		ucCfgONUNumLinks  Integer32,
		ucCfgONUnumQueuesUp  Integer32,
		ucCfgONUmaxQsPerLinkUp  Integer32,
		ucCfgONUqueueIncrUp  Integer32,
		ucCfgONUnumQueuesDn  Integer32,
		ucCfgONUmaxQsPerLinkDn  Integer32,
		ucCfgONUqueueIncrDn  Integer32,
		ucCfgONUupBuffer  Integer32,
		ucCfgONUdnBuffer  Integer32,
		ucCfgONUAuthenMode  INTEGER,
		ucCfgONUSN  DisplayString,
		ucCfgONUName  DisplayString,
		ucCfgONUQueueCfg  DisplayString,
		ucCfgONULinkStatus  INTEGER,
		ucCfgONUOperation  Integer32,
		ucCfgONUSnoopingDisable  Integer32,
		ucCfgONUMtu  Integer32
		}


	ucCfgONUSlotIndex	OBJECT-TYPE	
		SYNTAX			Integer32  ( 1 .. 16  ) 
		MAX-ACCESS		read-only
		STATUS			current
		DESCRIPTION		"Description."
		::=  {  ucCfgONUEntry  1  }


	ucCfgONUPonIndex	OBJECT-TYPE	
		SYNTAX			Integer32  ( 1 .. 32  ) 
		MAX-ACCESS		read-only
		STATUS			current
		DESCRIPTION		"Description."
		::=  {  ucCfgONUEntry  2  }


	ucCfgONUIndex	OBJECT-TYPE	
		SYNTAX			Integer32  ( 1 .. 256  ) 
		MAX-ACCESS		read-only
		STATUS			current
		DESCRIPTION		"Description."
		::=  {  ucCfgONUEntry  3  }


	ucCfgONUIeeeOui	OBJECT-TYPE	
		SYNTAX			DisplayString  ( SIZE ( 6 .. 6  ) ) 
		MAX-ACCESS		read-only
		STATUS			current
		DESCRIPTION		"Description."
		::=  {  ucCfgONUEntry  4  }


	ucCfgONUProductCode	OBJECT-TYPE	
		SYNTAX			DisplayString  ( SIZE ( 4 .. 4  ) ) 
		MAX-ACCESS		read-only
		STATUS			current
		DESCRIPTION		"Description."
		::=  {  ucCfgONUEntry  5  }


	ucCfgONUProductVersion	OBJECT-TYPE	
		SYNTAX			DisplayString  ( SIZE ( 4 .. 4  ) ) 
		MAX-ACCESS		read-only
		STATUS			current
		DESCRIPTION		"Description."
		::=  {  ucCfgONUEntry  6  }


	ucCfgONULLIDAssigned	OBJECT-TYPE	
		SYNTAX			Integer32  ( 0 .. 65535  ) 
		MAX-ACCESS		read-only
		STATUS			current
		DESCRIPTION		"Description."
		::=  {  ucCfgONUEntry  7  }


	ucCfgONUTKExtension	OBJECT-TYPE	
		SYNTAX			Integer32  ( 0 .. 65535  ) 
		MAX-ACCESS		read-only
		STATUS			current
		DESCRIPTION		"Description."
		::=  {  ucCfgONUEntry  8  }


	ucCfgONUFirmwareVersion	OBJECT-TYPE	
		SYNTAX			DisplayString  ( SIZE ( 4 .. 4  ) ) 
		MAX-ACCESS		read-only
		STATUS			current
		DESCRIPTION		"Description."
		::=  {  ucCfgONUEntry  9  }


	ucCfgONUVendorInfo	OBJECT-TYPE	
		SYNTAX			OCTET STRING  ( SIZE ( 64 .. 64  ) ) 
		MAX-ACCESS		read-only
		STATUS			current
		DESCRIPTION		"Description."
		::=  {  ucCfgONUEntry  10  }


	ucCfgONUPhysicalID	OBJECT-TYPE	
		SYNTAX			DisplayString  ( SIZE ( 12 .. 12  ) ) 
		MAX-ACCESS		read-only
		STATUS			current
		DESCRIPTION		"Description."
		::=  {  ucCfgONUEntry  11  }


	ucCfgONUMaxLinks	OBJECT-TYPE	
		SYNTAX			Integer32  ( 0 .. 255  ) 
		MAX-ACCESS		read-only
		STATUS			current
		DESCRIPTION		"Description."
		::=  {  ucCfgONUEntry  12  }


	ucCfgONUPorts	OBJECT-TYPE	
		SYNTAX			Integer32  ( 1 .. 24  ) 
		MAX-ACCESS		read-only
		STATUS			current
		DESCRIPTION		"Description."
		::=  {  ucCfgONUEntry  13  }


	ucCfgONUChipJedec	OBJECT-TYPE	
		SYNTAX			DisplayString  ( SIZE ( 4 .. 4  ) ) 
		MAX-ACCESS		read-only
		STATUS			current
		DESCRIPTION		"Description."
		::=  {  ucCfgONUEntry  14  }


	ucCfgONUChipID	OBJECT-TYPE	
		SYNTAX			DisplayString  ( SIZE ( 4 .. 4  ) ) 
		MAX-ACCESS		read-only
		STATUS			current
		DESCRIPTION		"Description."
		::=  {  ucCfgONUEntry  15  }


	ucCfgONUChipVersion	OBJECT-TYPE	
		SYNTAX			DisplayString  ( SIZE ( 4 .. 4  ) ) 
		MAX-ACCESS		read-only
		STATUS			current
		DESCRIPTION		"Description."
		::=  {  ucCfgONUEntry  16  }


	ucCfgONUBootVersion	OBJECT-TYPE	
		SYNTAX			DisplayString  ( SIZE ( 4 .. 4  ) ) 
		MAX-ACCESS		read-only
		STATUS			current
		DESCRIPTION		"Description."
		::=  {  ucCfgONUEntry  17  }


	ucCfgONUPersVersion	OBJECT-TYPE	
		SYNTAX			DisplayString  ( SIZE ( 4 .. 4  ) ) 
		MAX-ACCESS		read-only
		STATUS			current
		DESCRIPTION		"Description."
		::=  {  ucCfgONUEntry  18  }


	ucCfgONUApp0Version	OBJECT-TYPE	
		SYNTAX			DisplayString  ( SIZE ( 4 .. 4  ) ) 
		MAX-ACCESS		read-only
		STATUS			current
		DESCRIPTION		"Description."
		::=  {  ucCfgONUEntry  19  }


	ucCfgONUApp1Version	OBJECT-TYPE	
		SYNTAX			DisplayString  ( SIZE ( 4 .. 4  ) ) 
		MAX-ACCESS		read-only
		STATUS			current
		DESCRIPTION		"Description."
		::=  {  ucCfgONUEntry  20  }


	ucCfgONUDiagVersion	OBJECT-TYPE	
		SYNTAX			DisplayString  ( SIZE ( 4 .. 4  ) ) 
		MAX-ACCESS		read-only
		STATUS			current
		DESCRIPTION		"Description."
		::=  {  ucCfgONUEntry  21  }


	ucCfgONUReset	OBJECT-TYPE	
		SYNTAX			INTEGER  { nop ( 0 ) , yes ( 1 ) , no ( 2 ) } 
		MAX-ACCESS		read-write
		STATUS			current
		DESCRIPTION		"Description."
		::=  {  ucCfgONUEntry  22  }


	ucCfgONURestoreDefault	OBJECT-TYPE	
		SYNTAX			INTEGER  { nop ( 0 ) , yes ( 1 ) , no ( 2 ) } 
		MAX-ACCESS		read-write
		STATUS			current
		DESCRIPTION		"Description."
		::=  {  ucCfgONUEntry  23  }


	ucCfgONUUserTraffic	OBJECT-TYPE	
		SYNTAX			INTEGER  { enable ( 1 ) , disable ( 2 ) } 
		MAX-ACCESS		read-write
		STATUS			current
		DESCRIPTION		"Description."
		::=  {  ucCfgONUEntry  24  }


	ucCfgONURTT	OBJECT-TYPE	
		SYNTAX			Integer32  ( 1 .. 65535  ) 
		MAX-ACCESS		read-only
		STATUS			current
		DESCRIPTION		"Description."
		::=  {  ucCfgONUEntry  25  }


	ucCfgONUNumLinks	OBJECT-TYPE	
		SYNTAX			Integer32  ( 1 .. 16  ) 
		MAX-ACCESS		read-only
		STATUS			current
		DESCRIPTION		"Description."
		::=  {  ucCfgONUEntry  26  }


	ucCfgONUnumQueuesUp	OBJECT-TYPE	
		SYNTAX			Integer32  ( 1 .. 64  ) 
		MAX-ACCESS		read-only
		STATUS			current
		DESCRIPTION		"Description."
		::=  {  ucCfgONUEntry  27  }


	ucCfgONUmaxQsPerLinkUp	OBJECT-TYPE	
		SYNTAX			Integer32  ( 1 .. 64  ) 
		MAX-ACCESS		read-only
		STATUS			current
		DESCRIPTION		"Description."
		::=  {  ucCfgONUEntry  28  }


	ucCfgONUqueueIncrUp	OBJECT-TYPE	
		SYNTAX			Integer32  ( 1 .. 64  ) 
		MAX-ACCESS		read-only
		STATUS			current
		DESCRIPTION		"Description."
		::=  {  ucCfgONUEntry  29  }


	ucCfgONUnumQueuesDn	OBJECT-TYPE	
		SYNTAX			Integer32  ( 1 .. 64  ) 
		MAX-ACCESS		read-only
		STATUS			current
		DESCRIPTION		"Description."
		::=  {  ucCfgONUEntry  30  }


	ucCfgONUmaxQsPerLinkDn	OBJECT-TYPE	
		SYNTAX			Integer32  ( 1 .. 64  ) 
		MAX-ACCESS		read-only
		STATUS			current
		DESCRIPTION		"Description."
		::=  {  ucCfgONUEntry  31  }


	ucCfgONUqueueIncrDn	OBJECT-TYPE	
		SYNTAX			Integer32  ( 1 .. 64  ) 
		MAX-ACCESS		read-only
		STATUS			current
		DESCRIPTION		"Description."
		::=  {  ucCfgONUEntry  32  }


	ucCfgONUupBuffer	OBJECT-TYPE	
		SYNTAX			Integer32  ( 100 .. 2000  ) 
		MAX-ACCESS		read-only
		STATUS			current
		DESCRIPTION		"Description."
		::=  {  ucCfgONUEntry  33  }


	ucCfgONUdnBuffer	OBJECT-TYPE	
		SYNTAX			Integer32  ( 100 .. 2000  ) 
		MAX-ACCESS		read-only
		STATUS			current
		DESCRIPTION		"Description."
		::=  {  ucCfgONUEntry  34  }


	ucCfgONUAuthenMode	OBJECT-TYPE	
		SYNTAX			INTEGER  { undef ( 0 ) , pass ( 1 ) , deny ( 2 ) } 
		MAX-ACCESS		read-write
		STATUS			current
		DESCRIPTION		"Description."
		::=  {  ucCfgONUEntry  35  }


	ucCfgONUSN	OBJECT-TYPE	
		SYNTAX			DisplayString  ( SIZE ( 64 .. 64  ) ) 
		MAX-ACCESS		read-write
		STATUS			current
		DESCRIPTION		"Description."
		::=  {  ucCfgONUEntry  36  }


	ucCfgONUName	OBJECT-TYPE	
		SYNTAX			DisplayString  ( SIZE ( 32 .. 32  ) ) 
		MAX-ACCESS		read-write
		STATUS			current
		DESCRIPTION		"Description."
		::=  {  ucCfgONUEntry  37  }


	ucCfgONUQueueCfg	OBJECT-TYPE	
		SYNTAX			DisplayString  ( SIZE ( 16 .. 364  ) ) 
		MAX-ACCESS		read-write
		STATUS			current
		DESCRIPTION		"Description."
		::=  {  ucCfgONUEntry  38  }


	ucCfgONULinkStatus	OBJECT-TYPE	
		SYNTAX			INTEGER  { notexist ( 0 ) , online ( 1 ) , offline ( 2 ) , poweroff ( 3 ) } 
		MAX-ACCESS		read-only
		STATUS			current
		DESCRIPTION		"Description."
		::=  {  ucCfgONUEntry  39  }


	ucCfgONUOperation	OBJECT-TYPE	
		SYNTAX			Integer32  ( 0 .. 1  ) 
		MAX-ACCESS		read-write
		STATUS			current
		DESCRIPTION		"Size    Description 1 Operation(0=Nop,1=Delete)"
		::=  {  ucCfgONUEntry  40  }
		
	ucCfgONUSnoopingDisable	OBJECT-TYPE	
		SYNTAX			Integer32  {enableSnooping(0),disableSnooping(1)} 
		MAX-ACCESS		read-write
		STATUS			current
		DESCRIPTION		"Disable ONU IGMP-Snooping Function Control"
		::=  {  ucCfgONUEntry  41  }
	
	ucCfgONUMtu	OBJECT-TYPE	
		SYNTAX			Integer32  (1536 .. 1900)
		MAX-ACCESS		read-write
		STATUS			current
		DESCRIPTION		"Config ONU MTU value,default is 1536"
		::=  {  ucCfgONUEntry  42  }
		
				

	ucVlan	OBJECT IDENTIFIER
		::=  {  ucEthernet  1  }

	ucFrameFilter	OBJECT IDENTIFIER
		::=  {  ucEthernet  2  }

	ucIGMP	OBJECT IDENTIFIER
		::=  {  ucEthernet  3  }

	ucSysFunc	OBJECT IDENTIFIER
		::=  {  ucEthernet  4  }

	ucSysware	OBJECT IDENTIFIER
		::=  {  ucEthernet  5  }

	ucConfig	OBJECT IDENTIFIER
		::=  {  ucEthernet  6  }

	ucPortStat	OBJECT IDENTIFIER
		::=  {  ucPerformance  1  }

	ucAlarmTimesTable	OBJECT-TYPE
		SYNTAX		SEQUENCE  OF  UcAlarmTimesEntry
		MAX-ACCESS	not-accessible
		STATUS		current
		DESCRIPTION	"Description"
		::=  { ucAlarmMgmt  1 }

	ucAlarmTimesEntry	OBJECT-TYPE
		SYNTAX		UcAlarmTimesEntry
		MAX-ACCESS	not-accessible
		STATUS		current
		DESCRIPTION	"Description"
		INDEX		{  ucAlarmTimesSlotIndex, ucAlarmTimesPonIndex  }
		::=  { ucAlarmTimesTable 1 }

	UcAlarmTimesEntry  ::=  SEQUENCE {
		ucAlarmTimesSlotIndex  Integer32,
		ucAlarmTimesPonIndex  Integer32,
		ucAlarmTimesAlarmID  Integer32,
		ucAlarmTimesAlarmCtrl  INTEGER,
		ucAlarmTimesUntilSet  Integer32,
		ucAlarmTimesBeforeClear  Integer32
		}


	ucAlarmTimesSlotIndex	OBJECT-TYPE	
		SYNTAX			Integer32  ( 1 .. 16  ) 
		MAX-ACCESS		read-only
		STATUS			current
		DESCRIPTION		"Description."
		::=  {  ucAlarmTimesEntry  1  }


	ucAlarmTimesPonIndex	OBJECT-TYPE	
		SYNTAX			Integer32  ( 1 .. 32  ) 
		MAX-ACCESS		read-only
		STATUS			current
		DESCRIPTION		"Description."
		::=  {  ucAlarmTimesEntry  2  }


	ucAlarmTimesAlarmID	OBJECT-TYPE	
		SYNTAX			Integer32  ( 16 .. 154  ) 
		MAX-ACCESS		read-write
		STATUS			current
		DESCRIPTION		"Description."
		::=  {  ucAlarmTimesEntry  3  }


	ucAlarmTimesAlarmCtrl	OBJECT-TYPE	
		SYNTAX			INTEGER  { disable ( 1 ) , enable ( 2 ) } 
		MAX-ACCESS		read-write
		STATUS			current
		DESCRIPTION		"Description."
		::=  {  ucAlarmTimesEntry  4  }


	ucAlarmTimesUntilSet	OBJECT-TYPE	
		SYNTAX			Integer32  ( 0 .. 65400  ) 
		MAX-ACCESS		read-write
		STATUS			current
		DESCRIPTION		"Description."
		::=  {  ucAlarmTimesEntry  5  }


	ucAlarmTimesBeforeClear	OBJECT-TYPE	
		SYNTAX			Integer32  ( 0 .. 65400  ) 
		MAX-ACCESS		read-write
		STATUS			current
		DESCRIPTION		"Description."
		::=  {  ucAlarmTimesEntry  6  }

	ucAlarmOltPortTable	OBJECT-TYPE
		SYNTAX		SEQUENCE  OF  UcAlarmOltPortEntry
		MAX-ACCESS	not-accessible
		STATUS		current
		DESCRIPTION	"Description"
		::=  { ucAlarmMgmt  2 }

	ucAlarmOltPortEntry	OBJECT-TYPE
		SYNTAX		UcAlarmOltPortEntry
		MAX-ACCESS	not-accessible
		STATUS		current
		DESCRIPTION	"Description"
		INDEX		{  ucAlarmOltPortSlotIndex, ucAlarmOltPortPonIndex, ucAlarmOltPortPortIndex  }
		::=  { ucAlarmOltPortTable 1 }

	UcAlarmOltPortEntry  ::=  SEQUENCE {
		ucAlarmOltPortSlotIndex  Integer32,
		ucAlarmOltPortPonIndex  Integer32,
		ucAlarmOltPortPortIndex  Integer32,
		ucAlarmOltPortDir  INTEGER,
		ucAlarmOltPortStatID  Integer32,
		ucAlarmOltPortRisingThreshold  Counter32,
		ucAlarmOltPortFallingThreshold  Counter32
		}


	ucAlarmOltPortSlotIndex	OBJECT-TYPE	
		SYNTAX			Integer32  ( 1 .. 16  ) 
		MAX-ACCESS		read-only
		STATUS			current
		DESCRIPTION		"Description."
		::=  {  ucAlarmOltPortEntry  1  }


	ucAlarmOltPortPonIndex	OBJECT-TYPE	
		SYNTAX			Integer32  ( 1 .. 32  ) 
		MAX-ACCESS		read-only
		STATUS			current
		DESCRIPTION		"Description."
		::=  {  ucAlarmOltPortEntry  2  }


	ucAlarmOltPortPortIndex	OBJECT-TYPE	
		SYNTAX			Integer32  ( 1 .. 24  ) 
		MAX-ACCESS		read-only
		STATUS			current
		DESCRIPTION		"Description."
		::=  {  ucAlarmOltPortEntry  3  }


	ucAlarmOltPortDir	OBJECT-TYPE	
		SYNTAX			INTEGER  { downstream ( 1 ) , upstream ( 2 ) } 
		MAX-ACCESS		read-only
		STATUS			current
		DESCRIPTION		"Description."
		::=  {  ucAlarmOltPortEntry  4  }


	ucAlarmOltPortStatID	OBJECT-TYPE	
		SYNTAX			Integer32  ( 0 .. 54  ) 
		MAX-ACCESS		read-write
		STATUS			current
		DESCRIPTION		"Description."
		::=  {  ucAlarmOltPortEntry  5  }


	ucAlarmOltPortRisingThreshold	OBJECT-TYPE	
		SYNTAX			Counter32
		MAX-ACCESS		read-write
		STATUS			current
		DESCRIPTION		"Description."
		::=  {  ucAlarmOltPortEntry  6  }


	ucAlarmOltPortFallingThreshold	OBJECT-TYPE	
		SYNTAX			Counter32
		MAX-ACCESS		read-write
		STATUS			current
		DESCRIPTION		"Description."
		::=  {  ucAlarmOltPortEntry  7  }

	ucAlarmOnuPortTable	OBJECT-TYPE
		SYNTAX		SEQUENCE  OF  UcAlarmOnuPortEntry
		MAX-ACCESS	not-accessible
		STATUS		current
		DESCRIPTION	"Description"
		::=  { ucAlarmMgmt  3 }

	ucAlarmOnuPortEntry	OBJECT-TYPE
		SYNTAX		UcAlarmOnuPortEntry
		MAX-ACCESS	not-accessible
		STATUS		current
		DESCRIPTION	"Description"
		INDEX		{  ucAlarmOnuPortSlotIndex, ucAlarmOnuPortPonIndex, ucAlarmOnuPortOnuIndex, ucAlarmOnuPortIndex  }
		::=  { ucAlarmOnuPortTable 1 }

	UcAlarmOnuPortEntry  ::=  SEQUENCE {
		ucAlarmOnuPortSlotIndex  Integer32,
		ucAlarmOnuPortPonIndex  Integer32,
		ucAlarmOnuPortOnuIndex  Integer32,
		ucAlarmOnuPortIndex  Integer32,
		ucAlarmOnuPortDir  INTEGER,
		ucAlarmOnuPortStatID  Integer32,
		ucAlarmOnuPortRisingThreshold  Counter32,
		ucAlarmOnuPortFallingThreshold  Counter32
		}


	ucAlarmOnuPortSlotIndex	OBJECT-TYPE	
		SYNTAX			Integer32  ( 1 .. 16  ) 
		MAX-ACCESS		read-only
		STATUS			current
		DESCRIPTION		"Description."
		::=  {  ucAlarmOnuPortEntry  1  }


	ucAlarmOnuPortPonIndex	OBJECT-TYPE	
		SYNTAX			Integer32  ( 1 .. 32  ) 
		MAX-ACCESS		read-only
		STATUS			current
		DESCRIPTION		"Description."
		::=  {  ucAlarmOnuPortEntry  2  }


	ucAlarmOnuPortOnuIndex	OBJECT-TYPE	
		SYNTAX			Integer32  ( 1 .. 256  ) 
		MAX-ACCESS		read-only
		STATUS			current
		DESCRIPTION		"Description."
		::=  {  ucAlarmOnuPortEntry  3  }


	ucAlarmOnuPortIndex	OBJECT-TYPE	
		SYNTAX			Integer32  ( 1 .. 24  ) 
		MAX-ACCESS		read-only
		STATUS			current
		DESCRIPTION		"Description."
		::=  {  ucAlarmOnuPortEntry  4  }


	ucAlarmOnuPortDir	OBJECT-TYPE	
		SYNTAX			INTEGER  { downstream ( 1 ) , upstream ( 2 ) } 
		MAX-ACCESS		read-only
		STATUS			current
		DESCRIPTION		"Description."
		::=  {  ucAlarmOnuPortEntry  5  }


	ucAlarmOnuPortStatID	OBJECT-TYPE	
		SYNTAX			Integer32  ( 0 .. 54  ) 
		MAX-ACCESS		read-write
		STATUS			current
		DESCRIPTION		"Description."
		::=  {  ucAlarmOnuPortEntry  6  }


	ucAlarmOnuPortRisingThreshold	OBJECT-TYPE	
		SYNTAX			Counter32
		MAX-ACCESS		read-write
		STATUS			current
		DESCRIPTION		"Description."
		::=  {  ucAlarmOnuPortEntry  7  }


	ucAlarmOnuPortFallingThreshold	OBJECT-TYPE	
		SYNTAX			Counter32
		MAX-ACCESS		read-write
		STATUS			current
		DESCRIPTION		"Description."
		::=  {  ucAlarmOnuPortEntry  8  }

	ucAlarmOltLLIDTable	OBJECT-TYPE
		SYNTAX		SEQUENCE  OF  UcAlarmOltLLIDEntry
		MAX-ACCESS	not-accessible
		STATUS		current
		DESCRIPTION	"Description"
		::=  { ucAlarmMgmt  4 }

	ucAlarmOltLLIDEntry	OBJECT-TYPE
		SYNTAX		UcAlarmOltLLIDEntry
		MAX-ACCESS	not-accessible
		STATUS		current
		DESCRIPTION	"Description"
		INDEX		{  ucAlarmOltLLIDSlotIndex, ucAlarmOltLLIDPonIndex  }
		::=  { ucAlarmOltLLIDTable 1 }

	UcAlarmOltLLIDEntry  ::=  SEQUENCE {
		ucAlarmOltLLIDSlotIndex  Integer32,
		ucAlarmOltLLIDPonIndex  Integer32,
		ucAlarmOltLLID  DisplayString,
		ucAlarmOltLLIDDir  INTEGER,
		ucAlarmOltLLIDStatID  Integer32,
		ucAlarmOltLLIDRisingThreshold  Counter32,
		ucAlarmOltLLIDFallingThreshold  Counter32
		}


	ucAlarmOltLLIDSlotIndex	OBJECT-TYPE	
		SYNTAX			Integer32  ( 1 .. 16  ) 
		MAX-ACCESS		read-only
		STATUS			current
		DESCRIPTION		"Description."
		::=  {  ucAlarmOltLLIDEntry  1  }


	ucAlarmOltLLIDPonIndex	OBJECT-TYPE	
		SYNTAX			Integer32  ( 1 .. 32  ) 
		MAX-ACCESS		read-only
		STATUS			current
		DESCRIPTION		"Description."
		::=  {  ucAlarmOltLLIDEntry  2  }


	ucAlarmOltLLID	OBJECT-TYPE	
		SYNTAX			DisplayString  ( SIZE ( 12 .. 12  ) ) 
		MAX-ACCESS		read-only
		STATUS			current
		DESCRIPTION		"Description."
		::=  {  ucAlarmOltLLIDEntry  3  }


	ucAlarmOltLLIDDir	OBJECT-TYPE	
		SYNTAX			INTEGER  { downstream ( 1 ) , upstream ( 2 ) } 
		MAX-ACCESS		read-only
		STATUS			current
		DESCRIPTION		"Description."
		::=  {  ucAlarmOltLLIDEntry  4  }


	ucAlarmOltLLIDStatID	OBJECT-TYPE	
		SYNTAX			Integer32  ( 0 .. 54  ) 
		MAX-ACCESS		read-write
		STATUS			current
		DESCRIPTION		"Description."
		::=  {  ucAlarmOltLLIDEntry  5  }


	ucAlarmOltLLIDRisingThreshold	OBJECT-TYPE	
		SYNTAX			Counter32
		MAX-ACCESS		read-write
		STATUS			current
		DESCRIPTION		"Description."
		::=  {  ucAlarmOltLLIDEntry  6  }


	ucAlarmOltLLIDFallingThreshold	OBJECT-TYPE	
		SYNTAX			Counter32
		MAX-ACCESS		read-write
		STATUS			current
		DESCRIPTION		"Description."
		::=  {  ucAlarmOltLLIDEntry  7  }

	ucAlarmOnuLLIDTable	OBJECT-TYPE
		SYNTAX		SEQUENCE  OF  UcAlarmOnuLLIDEntry
		MAX-ACCESS	not-accessible
		STATUS		current
		DESCRIPTION	"Description"
		::=  { ucAlarmMgmt  5 }

	ucAlarmOnuLLIDEntry	OBJECT-TYPE
		SYNTAX		UcAlarmOnuLLIDEntry
		MAX-ACCESS	not-accessible
		STATUS		current
		DESCRIPTION	"Description"
		INDEX		{  ucAlarmOnuLLIDSlotIndex, ucAlarmOnuLLIDPonIndex, ucAlarmOnuLLIDOnuIndex  }
		::=  { ucAlarmOnuLLIDTable 1 }

	UcAlarmOnuLLIDEntry  ::=  SEQUENCE {
		ucAlarmOnuLLIDSlotIndex  Integer32,
		ucAlarmOnuLLIDPonIndex  Integer32,
		ucAlarmOnuLLIDOnuIndex  Integer32,
		ucAlarmOnuLLIDIndex  Integer32,
		ucAlarmOnuLLIDDir  INTEGER,
		ucAlarmOnuLLIDStatID  Integer32,
		ucAlarmOnuLLIDRisingThreshold  Counter32,
		ucAlarmOnuLLIDFallingThreshold  Counter32
		}


	ucAlarmOnuLLIDSlotIndex	OBJECT-TYPE	
		SYNTAX			Integer32  ( 1 .. 16  ) 
		MAX-ACCESS		read-only
		STATUS			current
		DESCRIPTION		"Description."
		::=  {  ucAlarmOnuLLIDEntry  1  }


	ucAlarmOnuLLIDPonIndex	OBJECT-TYPE	
		SYNTAX			Integer32  ( 1 .. 32  ) 
		MAX-ACCESS		read-only
		STATUS			current
		DESCRIPTION		"Description."
		::=  {  ucAlarmOnuLLIDEntry  2  }


	ucAlarmOnuLLIDOnuIndex	OBJECT-TYPE	
		SYNTAX			Integer32  ( 1 .. 256  ) 
		MAX-ACCESS		read-only
		STATUS			current
		DESCRIPTION		"Description."
		::=  {  ucAlarmOnuLLIDEntry  3  }


	ucAlarmOnuLLIDIndex	OBJECT-TYPE	
		SYNTAX			Integer32
		MAX-ACCESS		read-only
		STATUS			current
		DESCRIPTION		"Description."
		::=  {  ucAlarmOnuLLIDEntry  4  }


	ucAlarmOnuLLIDDir	OBJECT-TYPE	
		SYNTAX			INTEGER  { downstream ( 1 ) , upstream ( 2 ) } 
		MAX-ACCESS		read-only
		STATUS			current
		DESCRIPTION		"Description."
		::=  {  ucAlarmOnuLLIDEntry  5  }


	ucAlarmOnuLLIDStatID	OBJECT-TYPE	
		SYNTAX			Integer32  ( 0 .. 54  ) 
		MAX-ACCESS		read-write
		STATUS			current
		DESCRIPTION		"Description."
		::=  {  ucAlarmOnuLLIDEntry  6  }


	ucAlarmOnuLLIDRisingThreshold	OBJECT-TYPE	
		SYNTAX			Counter32
		MAX-ACCESS		read-write
		STATUS			current
		DESCRIPTION		"Description."
		::=  {  ucAlarmOnuLLIDEntry  7  }


	ucAlarmOnuLLIDFallingThreshold	OBJECT-TYPE	
		SYNTAX			Counter32
		MAX-ACCESS		read-write
		STATUS			current
		DESCRIPTION		"Description."
		::=  {  ucAlarmOnuLLIDEntry  8  }

	ucAlarmOltQueryTable	OBJECT-TYPE
		SYNTAX		SEQUENCE  OF  UcAlarmOltQueryEntry
		MAX-ACCESS	not-accessible
		STATUS		current
		DESCRIPTION	"Description"
		::=  { ucAlarmMgmt  6 }

	ucAlarmOltQueryEntry	OBJECT-TYPE
		SYNTAX		UcAlarmOltQueryEntry
		MAX-ACCESS	not-accessible
		STATUS		current
		DESCRIPTION	"Description"
		INDEX		{  ucAlarmOltQuarySlotIndex, ucAlarmOltQuaryAlarmIndex, ucAlarmOltLLIDQueryDir  }
		::=  { ucAlarmOltQueryTable 1 }

	UcAlarmOltQueryEntry  ::=  SEQUENCE {
		ucAlarmOltQuarySlotIndex  Integer32,
		ucAlarmOltQuaryAlarmIndex  Integer32,
		ucAlarmOltQuaryAlarmID  Integer32,
		ucAlarmOltQuaryStatID  Integer32,
		ucAlarmOltQuaryDir  INTEGER,
		ucAlarmOltQuaryAlarmState  INTEGER,
		ucAlarmOltQuaryAlarmCnt  Integer32
		}


	ucAlarmOltQuarySlotIndex	OBJECT-TYPE	
		SYNTAX			Integer32  ( 1 .. 16  ) 
		MAX-ACCESS		read-only
		STATUS			current
		DESCRIPTION		"Description."
		::=  {  ucAlarmOltQueryEntry  1  }


	ucAlarmOltQuaryAlarmIndex	OBJECT-TYPE	
		SYNTAX			Integer32  ( 1 .. 255  ) 
		MAX-ACCESS		read-only
		STATUS			current
		DESCRIPTION		"Description."
		::=  {  ucAlarmOltQueryEntry  2  }


	ucAlarmOltQuaryAlarmID	OBJECT-TYPE	
		SYNTAX			Integer32  ( 16 .. 154  ) 
		MAX-ACCESS		read-only
		STATUS			current
		DESCRIPTION		"Description."
		::=  {  ucAlarmOltQueryEntry  3  }


	ucAlarmOltQuaryStatID	OBJECT-TYPE	
		SYNTAX			Integer32  ( 0 .. 54  ) 
		MAX-ACCESS		read-only
		STATUS			current
		DESCRIPTION		"Description."
		::=  {  ucAlarmOltQueryEntry  4  }


	ucAlarmOltQuaryDir	OBJECT-TYPE	
		SYNTAX			INTEGER  { downstream ( 1 ) , upstream ( 2 ) } 
		MAX-ACCESS		read-only
		STATUS			current
		DESCRIPTION		"Description."
		::=  {  ucAlarmOltQueryEntry  5  }


	ucAlarmOltQuaryAlarmState	OBJECT-TYPE	
		SYNTAX			INTEGER  { on ( 1 ) , off ( 2 ) } 
		MAX-ACCESS		read-only
		STATUS			current
		DESCRIPTION		"Description."
		::=  {  ucAlarmOltQueryEntry  6  }


	ucAlarmOltQuaryAlarmCnt	OBJECT-TYPE	
		SYNTAX			Integer32  ( 0 .. 255  ) 
		MAX-ACCESS		read-only
		STATUS			current
		DESCRIPTION		"Description."
		::=  {  ucAlarmOltQueryEntry  7  }

	ucAlarmOltLLIDQueryTable	OBJECT-TYPE
		SYNTAX		SEQUENCE  OF  UcAlarmOltLLIDQueryEntry
		MAX-ACCESS	not-accessible
		STATUS		current
		DESCRIPTION	"Description"
		::=  { ucAlarmMgmt  7 }

	ucAlarmOltLLIDQueryEntry	OBJECT-TYPE
		SYNTAX		UcAlarmOltLLIDQueryEntry
		MAX-ACCESS	not-accessible
		STATUS		current
		DESCRIPTION	"Description"
		INDEX		{  ucAlarmOltLLIDQuerySlotIndex, ucAlarmOltLLIDQueryPonIndex, ucAlarmOltLLIDQueryOltLLID, ucAlarmOltLLIDQueryAlarmIndex  }
		::=  { ucAlarmOltLLIDQueryTable 1 }

	UcAlarmOltLLIDQueryEntry  ::=  SEQUENCE {
		ucAlarmOltLLIDQuerySlotIndex  Integer32,
		ucAlarmOltLLIDQueryPonIndex  Integer32,
		ucAlarmOltLLIDQueryOltLLID  OCTET STRING,
		ucAlarmOltLLIDQueryAlarmIndex  Integer32,
		ucAlarmOltLLIDQueryAlarmID  Integer32,
		ucAlarmOltLLIDQueryStatID  Integer32,
		ucAlarmOltLLIDQueryDir  INTEGER,
		ucAlarmOltLLIDQueryAlarmState  INTEGER,
		ucAlarmOltLLIDQueryAlarmCnt  Integer32
		}


	ucAlarmOltLLIDQuerySlotIndex	OBJECT-TYPE	
		SYNTAX			Integer32  ( 1 .. 16  ) 
		MAX-ACCESS		read-only
		STATUS			current
		DESCRIPTION		"Description."
		::=  {  ucAlarmOltLLIDQueryEntry  1  }


	ucAlarmOltLLIDQueryPonIndex	OBJECT-TYPE	
		SYNTAX			Integer32  ( 1 .. 32  ) 
		MAX-ACCESS		read-only
		STATUS			current
		DESCRIPTION		"Description."
		::=  {  ucAlarmOltLLIDQueryEntry  2  }


	ucAlarmOltLLIDQueryOltLLID	OBJECT-TYPE	
		SYNTAX			OCTET STRING
		MAX-ACCESS		read-only
		STATUS			current
		DESCRIPTION		"Description."
		::=  {  ucAlarmOltLLIDQueryEntry  3  }


	ucAlarmOltLLIDQueryAlarmIndex	OBJECT-TYPE	
		SYNTAX			Integer32  ( 1 .. 255  ) 
		MAX-ACCESS		read-only
		STATUS			current
		DESCRIPTION		"Description."
		::=  {  ucAlarmOltLLIDQueryEntry  4  }


	ucAlarmOltLLIDQueryAlarmID	OBJECT-TYPE	
		SYNTAX			Integer32  ( 16 .. 154  ) 
		MAX-ACCESS		read-only
		STATUS			current
		DESCRIPTION		"Description."
		::=  {  ucAlarmOltLLIDQueryEntry  5  }


	ucAlarmOltLLIDQueryStatID	OBJECT-TYPE	
		SYNTAX			Integer32  ( 0 .. 54  ) 
		MAX-ACCESS		read-only
		STATUS			current
		DESCRIPTION		"Description."
		::=  {  ucAlarmOltLLIDQueryEntry  6  }


	ucAlarmOltLLIDQueryDir	OBJECT-TYPE	
		SYNTAX			INTEGER  { downstream ( 1 ) , upstream ( 2 ) } 
		MAX-ACCESS		read-only
		STATUS			current
		DESCRIPTION		"Description."
		::=  {  ucAlarmOltLLIDQueryEntry  7  }


	ucAlarmOltLLIDQueryAlarmState	OBJECT-TYPE	
		SYNTAX			INTEGER  { on ( 1 ) , off ( 2 ) } 
		MAX-ACCESS		read-only
		STATUS			current
		DESCRIPTION		"Description."
		::=  {  ucAlarmOltLLIDQueryEntry  8  }


	ucAlarmOltLLIDQueryAlarmCnt	OBJECT-TYPE	
		SYNTAX			Integer32  ( 0 .. 255  ) 
		MAX-ACCESS		read-only
		STATUS			current
		DESCRIPTION		"Description."
		::=  {  ucAlarmOltLLIDQueryEntry  9  }

	ucAlarmOltPortQueryTable	OBJECT-TYPE
		SYNTAX		SEQUENCE  OF  UcAlarmOltPortQueryEntry
		MAX-ACCESS	not-accessible
		STATUS		current
		DESCRIPTION	"Description"
		::=  { ucAlarmMgmt  8 }

	ucAlarmOltPortQueryEntry	OBJECT-TYPE
		SYNTAX		UcAlarmOltPortQueryEntry
		MAX-ACCESS	not-accessible
		STATUS		current
		DESCRIPTION	"Description"
		INDEX		{  ucAlarmOltPortQuerySlotIndex, ucAlarmOltPortQueryPonIndex, ucAlarmOltPortQueryPortIndex, ucAlarmOltPortQueryAlarmIndex  }
		::=  { ucAlarmOltPortQueryTable 1 }

	UcAlarmOltPortQueryEntry  ::=  SEQUENCE {
		ucAlarmOltPortQuerySlotIndex  Integer32,
		ucAlarmOltPortQueryPonIndex  Integer32,
		ucAlarmOltPortQueryPortIndex  Integer32,
		ucAlarmOltPortQueryAlarmIndex  Integer32,
		ucAlarmOltPortQueryAlarmID  Integer32,
		ucAlarmOltPortQueryStatID  Integer32,
		ucAlarmOltPortQueryDir  INTEGER,
		ucAlarmOltPortQueryAlarmState  INTEGER,
		ucAlarmOltPortQueryAlarmCnt  Integer32
		}


	ucAlarmOltPortQuerySlotIndex	OBJECT-TYPE	
		SYNTAX			Integer32  ( 1 .. 16  ) 
		MAX-ACCESS		read-only
		STATUS			current
		DESCRIPTION		"Description."
		::=  {  ucAlarmOltPortQueryEntry  1  }


	ucAlarmOltPortQueryPonIndex	OBJECT-TYPE	
		SYNTAX			Integer32  ( 1 .. 32  ) 
		MAX-ACCESS		read-only
		STATUS			current
		DESCRIPTION		"Description."
		::=  {  ucAlarmOltPortQueryEntry  2  }


	ucAlarmOltPortQueryPortIndex	OBJECT-TYPE	
		SYNTAX			Integer32  ( 1 .. 24  ) 
		MAX-ACCESS		read-only
		STATUS			current
		DESCRIPTION		"Description."
		::=  {  ucAlarmOltPortQueryEntry  3  }


	ucAlarmOltPortQueryAlarmIndex	OBJECT-TYPE	
		SYNTAX			Integer32  ( 1 .. 255  ) 
		MAX-ACCESS		read-only
		STATUS			current
		DESCRIPTION		"Description."
		::=  {  ucAlarmOltPortQueryEntry  4  }


	ucAlarmOltPortQueryAlarmID	OBJECT-TYPE	
		SYNTAX			Integer32  ( 16 .. 154  ) 
		MAX-ACCESS		read-only
		STATUS			current
		DESCRIPTION		"Description."
		::=  {  ucAlarmOltPortQueryEntry  5  }


	ucAlarmOltPortQueryStatID	OBJECT-TYPE	
		SYNTAX			Integer32  ( 0 .. 54  ) 
		MAX-ACCESS		read-only
		STATUS			current
		DESCRIPTION		"Description."
		::=  {  ucAlarmOltPortQueryEntry  6  }


	ucAlarmOltPortQueryDir	OBJECT-TYPE	
		SYNTAX			INTEGER  { downstream ( 1 ) , upstream ( 2 ) } 
		MAX-ACCESS		read-only
		STATUS			current
		DESCRIPTION		"Description."
		::=  {  ucAlarmOltPortQueryEntry  7  }


	ucAlarmOltPortQueryAlarmState	OBJECT-TYPE	
		SYNTAX			INTEGER  { on ( 1 ) , off ( 2 ) } 
		MAX-ACCESS		read-only
		STATUS			current
		DESCRIPTION		"Description."
		::=  {  ucAlarmOltPortQueryEntry  8  }


	ucAlarmOltPortQueryAlarmCnt	OBJECT-TYPE	
		SYNTAX			Integer32  ( 0 .. 255  ) 
		MAX-ACCESS		read-only
		STATUS			current
		DESCRIPTION		"Description."
		::=  {  ucAlarmOltPortQueryEntry  9  }

	ucAlarmOnuLLIDQueryTable	OBJECT-TYPE
		SYNTAX		SEQUENCE  OF  UcAlarmOnuLLIDQueryEntry
		MAX-ACCESS	not-accessible
		STATUS		current
		DESCRIPTION	"Description"
		::=  { ucAlarmMgmt  9 }

	ucAlarmOnuLLIDQueryEntry	OBJECT-TYPE
		SYNTAX		UcAlarmOnuLLIDQueryEntry
		MAX-ACCESS	not-accessible
		STATUS		current
		DESCRIPTION	"Description"
		INDEX		{  ucAlarmOnuLLIDQuerySlotIndex, ucAlarmOnuLLIDQueryPonIndex, ucAlarmOnuLLIDQueryOnuIndex, ucAlarmOnuLLIDQueryAlarmIndex, ucAlarmOnuLLIDQueryLLIDIndex  }
		::=  { ucAlarmOnuLLIDQueryTable 1 }

	UcAlarmOnuLLIDQueryEntry  ::=  SEQUENCE {
		ucAlarmOnuLLIDQuerySlotIndex  Integer32,
		ucAlarmOnuLLIDQueryPonIndex  Integer32,
		ucAlarmOnuLLIDQueryOnuIndex  Integer32,
		ucAlarmOnuLLIDQueryLLIDIndex  Integer32,
		ucAlarmOnuLLIDQueryAlarmIndex  Integer32,
		ucAlarmOnuLLIDQueryAlarmID  Integer32,
		ucAlarmOnuLLIDQueryStatID  Integer32,
		ucAlarmOnuLLIDQueryDir  INTEGER,
		ucAlarmOnuLLIDQueryAlarmState  INTEGER,
		ucAlarmOnuLLIDQueryAlarmCnt  Integer32
		}


	ucAlarmOnuLLIDQuerySlotIndex	OBJECT-TYPE	
		SYNTAX			Integer32  ( 1 .. 16  ) 
		MAX-ACCESS		read-only
		STATUS			current
		DESCRIPTION		"Description."
		::=  {  ucAlarmOnuLLIDQueryEntry  1  }


	ucAlarmOnuLLIDQueryPonIndex	OBJECT-TYPE	
		SYNTAX			Integer32  ( 1 .. 32  ) 
		MAX-ACCESS		read-only
		STATUS			current
		DESCRIPTION		"Description."
		::=  {  ucAlarmOnuLLIDQueryEntry  2  }


	ucAlarmOnuLLIDQueryOnuIndex	OBJECT-TYPE	
		SYNTAX			Integer32  ( 1 .. 256  ) 
		MAX-ACCESS		read-only
		STATUS			current
		DESCRIPTION		"Description."
		::=  {  ucAlarmOnuLLIDQueryEntry  3  }


	ucAlarmOnuLLIDQueryLLIDIndex	OBJECT-TYPE	
		SYNTAX			Integer32  ( 1 .. 8  ) 
		MAX-ACCESS		read-only
		STATUS			current
		DESCRIPTION		"Description."
		::=  {  ucAlarmOnuLLIDQueryEntry  4  }


	ucAlarmOnuLLIDQueryAlarmIndex	OBJECT-TYPE	
		SYNTAX			Integer32  ( 1 .. 255  ) 
		MAX-ACCESS		read-only
		STATUS			current
		DESCRIPTION		"Description."
		::=  {  ucAlarmOnuLLIDQueryEntry  5  }


	ucAlarmOnuLLIDQueryAlarmID	OBJECT-TYPE	
		SYNTAX			Integer32  ( 16 .. 154  ) 
		MAX-ACCESS		read-only
		STATUS			current
		DESCRIPTION		"Description."
		::=  {  ucAlarmOnuLLIDQueryEntry  6  }


	ucAlarmOnuLLIDQueryStatID	OBJECT-TYPE	
		SYNTAX			Integer32  ( 0 .. 54  ) 
		MAX-ACCESS		read-only
		STATUS			current
		DESCRIPTION		"Description."
		::=  {  ucAlarmOnuLLIDQueryEntry  7  }


	ucAlarmOnuLLIDQueryDir	OBJECT-TYPE	
		SYNTAX			INTEGER  { downstream ( 1 ) , upstream ( 2 ) } 
		MAX-ACCESS		read-only
		STATUS			current
		DESCRIPTION		"Description."
		::=  {  ucAlarmOnuLLIDQueryEntry  8  }


	ucAlarmOnuLLIDQueryAlarmState	OBJECT-TYPE	
		SYNTAX			INTEGER  { on ( 1 ) , off ( 2 ) } 
		MAX-ACCESS		read-only
		STATUS			current
		DESCRIPTION		"Description."
		::=  {  ucAlarmOnuLLIDQueryEntry  9  }


	ucAlarmOnuLLIDQueryAlarmCnt	OBJECT-TYPE	
		SYNTAX			Integer32  ( 0 .. 255  ) 
		MAX-ACCESS		read-only
		STATUS			current
		DESCRIPTION		"Description."
		::=  {  ucAlarmOnuLLIDQueryEntry  10  }

	ucAlarmOnuPortQueryTable	OBJECT-TYPE
		SYNTAX		SEQUENCE  OF  UcAlarmOnuPortQueryEntry
		MAX-ACCESS	not-accessible
		STATUS		current
		DESCRIPTION	"Description"
		::=  { ucAlarmMgmt  10 }

	ucAlarmOnuPortQueryEntry	OBJECT-TYPE
		SYNTAX		UcAlarmOnuPortQueryEntry
		MAX-ACCESS	not-accessible
		STATUS		current
		DESCRIPTION	"Description"
		INDEX		{  ucAlarmOnuPortQuerySlotIndex, ucAlarmOnuPortQueryPonIndex, ucAlarmOnuPortQueryOnuIndex, ucAlarmOnuPortQueryPortIndex, ucAlarmOnuPortQueryAlarmIndex  }
		::=  { ucAlarmOnuPortQueryTable 1 }

	UcAlarmOnuPortQueryEntry  ::=  SEQUENCE {
		ucAlarmOnuPortQuerySlotIndex  Integer32,
		ucAlarmOnuPortQueryPonIndex  Integer32,
		ucAlarmOnuPortQueryOnuIndex  Integer32,
		ucAlarmOnuPortQueryPortIndex  Integer32,
		ucAlarmOnuPortQueryAlarmIndex  Integer32,
		ucAlarmOnuPortQueryAlarmID  Integer32,
		ucAlarmOnuPortQueryStatID  Integer32,
		ucAlarmOnuPortQueryDir  INTEGER,
		ucAlarmOnuPortQueryAlarmState  INTEGER,
		ucAlarmOnuPortQueryAlarmCnt  Integer32
		}


	ucAlarmOnuPortQuerySlotIndex	OBJECT-TYPE	
		SYNTAX			Integer32  ( 1 .. 16  ) 
		MAX-ACCESS		read-only
		STATUS			current
		DESCRIPTION		"Description."
		::=  {  ucAlarmOnuPortQueryEntry  1  }


	ucAlarmOnuPortQueryPonIndex	OBJECT-TYPE	
		SYNTAX			Integer32  ( 1 .. 32  ) 
		MAX-ACCESS		read-only
		STATUS			current
		DESCRIPTION		"Description."
		::=  {  ucAlarmOnuPortQueryEntry  2  }


	ucAlarmOnuPortQueryOnuIndex	OBJECT-TYPE	
		SYNTAX			Integer32  ( 1 .. 256  ) 
		MAX-ACCESS		read-only
		STATUS			current
		DESCRIPTION		"Description."
		::=  {  ucAlarmOnuPortQueryEntry  3  }


	ucAlarmOnuPortQueryPortIndex	OBJECT-TYPE	
		SYNTAX			Integer32  ( 1 .. 24  ) 
		MAX-ACCESS		read-only
		STATUS			current
		DESCRIPTION		"Description."
		::=  {  ucAlarmOnuPortQueryEntry  4  }


	ucAlarmOnuPortQueryAlarmIndex	OBJECT-TYPE	
		SYNTAX			Integer32  ( 1 .. 255  ) 
		MAX-ACCESS		read-only
		STATUS			current
		DESCRIPTION		"Description."
		::=  {  ucAlarmOnuPortQueryEntry  5  }


	ucAlarmOnuPortQueryAlarmID	OBJECT-TYPE	
		SYNTAX			Integer32  ( 16 .. 154  ) 
		MAX-ACCESS		read-only
		STATUS			current
		DESCRIPTION		"Description."
		::=  {  ucAlarmOnuPortQueryEntry  6  }


	ucAlarmOnuPortQueryStatID	OBJECT-TYPE	
		SYNTAX			Integer32  ( 0 .. 54  ) 
		MAX-ACCESS		read-only
		STATUS			current
		DESCRIPTION		"Description."
		::=  {  ucAlarmOnuPortQueryEntry  7  }


	ucAlarmOnuPortQueryDir	OBJECT-TYPE	
		SYNTAX			INTEGER  { downstream ( 1 ) , upstream ( 2 ) } 
		MAX-ACCESS		read-only
		STATUS			current
		DESCRIPTION		"Description."
		::=  {  ucAlarmOnuPortQueryEntry  8  }


	ucAlarmOnuPortQueryAlarmState	OBJECT-TYPE	
		SYNTAX			INTEGER  { on ( 1 ) , off ( 2 ) } 
		MAX-ACCESS		read-only
		STATUS			current
		DESCRIPTION		"Description."
		::=  {  ucAlarmOnuPortQueryEntry  9  }


	ucAlarmOnuPortQueryAlarmCnt	OBJECT-TYPE	
		SYNTAX			Integer32  ( 0 .. 255  ) 
		MAX-ACCESS		read-only
		STATUS			current
		DESCRIPTION		"Description."
		::=  {  ucAlarmOnuPortQueryEntry  10  }

	ucAlarmOnuQueryTable	OBJECT-TYPE
		SYNTAX		SEQUENCE  OF  UcAlarmOnuQueryEntry
		MAX-ACCESS	not-accessible
		STATUS		current
		DESCRIPTION	"Description"
		::=  { ucAlarmMgmt  11 }

	ucAlarmOnuQueryEntry	OBJECT-TYPE
		SYNTAX		UcAlarmOnuQueryEntry
		MAX-ACCESS	not-accessible
		STATUS		current
		DESCRIPTION	"Description"
		INDEX		{  ucAlarmOnuQuerySlotIndex, ucAlarmOnuQueryPonIndex, ucAlarmOnuQueryOnuIndex, ucAlarmOnuQueryAlarmIndex  }
		::=  { ucAlarmOnuQueryTable 1 }

	UcAlarmOnuQueryEntry  ::=  SEQUENCE {
		ucAlarmOnuQuerySlotIndex  Integer32,
		ucAlarmOnuQueryPonIndex  Integer32,
		ucAlarmOnuQueryOnuIndex  Integer32,
		ucAlarmOnuQueryAlarmIndex  Integer32,
		ucAlarmOnuQueryAlarmID  Integer32,
		ucAlarmOnuQueryStatID  Integer32,
		ucAlarmOnuQueryDir  INTEGER,
		ucAlarmOnuQueryAlarmState  INTEGER,
		ucAlarmOnuQueryAlarmCnt  Integer32
		}


	ucAlarmOnuQuerySlotIndex	OBJECT-TYPE	
		SYNTAX			Integer32  ( 1 .. 16  ) 
		MAX-ACCESS		read-only
		STATUS			current
		DESCRIPTION		"Description."
		::=  {  ucAlarmOnuQueryEntry  1  }


	ucAlarmOnuQueryPonIndex	OBJECT-TYPE	
		SYNTAX			Integer32  ( 1 .. 32  ) 
		MAX-ACCESS		read-only
		STATUS			current
		DESCRIPTION		"Description."
		::=  {  ucAlarmOnuQueryEntry  2  }


	ucAlarmOnuQueryOnuIndex	OBJECT-TYPE	
		SYNTAX			Integer32  ( 1 .. 256  ) 
		MAX-ACCESS		read-only
		STATUS			current
		DESCRIPTION		"Description."
		::=  {  ucAlarmOnuQueryEntry  3  }


	ucAlarmOnuQueryAlarmIndex	OBJECT-TYPE	
		SYNTAX			Integer32  ( 1 .. 255  ) 
		MAX-ACCESS		read-only
		STATUS			current
		DESCRIPTION		"Description."
		::=  {  ucAlarmOnuQueryEntry  4  }


	ucAlarmOnuQueryAlarmID	OBJECT-TYPE	
		SYNTAX			Integer32  ( 16 .. 154  ) 
		MAX-ACCESS		read-only
		STATUS			current
		DESCRIPTION		"Description."
		::=  {  ucAlarmOnuQueryEntry  5  }


	ucAlarmOnuQueryStatID	OBJECT-TYPE	
		SYNTAX			Integer32  ( 0 .. 54  ) 
		MAX-ACCESS		read-only
		STATUS			current
		DESCRIPTION		"Description."
		::=  {  ucAlarmOnuQueryEntry  6  }


	ucAlarmOnuQueryDir	OBJECT-TYPE	
		SYNTAX			INTEGER  { downstream ( 1 ) , upstream ( 2 ) } 
		MAX-ACCESS		read-only
		STATUS			current
		DESCRIPTION		"Description."
		::=  {  ucAlarmOnuQueryEntry  7  }


	ucAlarmOnuQueryAlarmState	OBJECT-TYPE	
		SYNTAX			INTEGER  { on ( 1 ) , off ( 2 ) } 
		MAX-ACCESS		read-only
		STATUS			current
		DESCRIPTION		"Description."
		::=  {  ucAlarmOnuQueryEntry  8  }


	ucAlarmOnuQueryAlarmCnt	OBJECT-TYPE	
		SYNTAX			Integer32  ( 0 .. 255  ) 
		MAX-ACCESS		read-only
		STATUS			current
		DESCRIPTION		"Description."
		::=  {  ucAlarmOnuQueryEntry  9  }

	ucOltPppoeParaTable	OBJECT-TYPE
		SYNTAX		SEQUENCE  OF  UcOltPppoeParaEntry
		MAX-ACCESS	not-accessible
		STATUS		current
		DESCRIPTION	"Description"
		::=  { ucAuthentication  1 }

	ucOltPppoeParaEntry	OBJECT-TYPE
		SYNTAX		UcOltPppoeParaEntry
		MAX-ACCESS	not-accessible
		STATUS		current
		DESCRIPTION	"Description"
		INDEX		{  ucPppoeSlotIndex, ucPppoePonIndex  }
		::=  { ucOltPppoeParaTable 1 }

	UcOltPppoeParaEntry  ::=  SEQUENCE {
		ucPppoeSlotIndex  Integer32,
		ucPppoePonIndex  Integer32,
		ucPppoeParaCtrl  DisplayString,
		ucPppoeEntrys  DisplayString,
		ucPppoeOperatin  INTEGER
		}


	ucPppoeSlotIndex	OBJECT-TYPE	
		SYNTAX			Integer32  ( 1 .. 16  ) 
		MAX-ACCESS		read-only
		STATUS			current
		DESCRIPTION		"Description."
		::=  {  ucOltPppoeParaEntry  1  }


	ucPppoePonIndex	OBJECT-TYPE	
		SYNTAX			Integer32  ( 1 .. 32  ) 
		MAX-ACCESS		read-only
		STATUS			current
		DESCRIPTION		"Description."
		::=  {  ucOltPppoeParaEntry  2  }


	ucPppoeParaCtrl	OBJECT-TYPE	
		SYNTAX			DisplayString
		MAX-ACCESS		read-write
		STATUS			current
		DESCRIPTION		"Size    Description
2 PPPoE Mode Bits (0 = All PPPoE features Disabled)----Default(0)
   (Bit 0: PPPoE Snooping / MAC Learning Enable
   Bit 1: Send PADT to Server (upstream) on Session timeout
   Bit 2: Send PADT to Client (downstream) on Session timeout
   Bit 3 - Bit15: Reserved)
2 Maximum number of learned PPPoE Client MAC addresses----Default(0)--Min(0)--Max(3839)
2 Minimum Guaranteed number of PPPoE Client MAC addresses----Default(0)--Min(0)--Max(3839)
2 Maximum number of PPPoE Sessions per PPPoE Client ----Default(4)--Min(1)--Max(4)
2 PPPoE Timer Interval ----Units(Seconds)--Default(10)--Min(1)--Max(65535)
2 PPPoE Response Timer Ticks (PPPoE Timer Intervals) ----Units(Ticks)--Default( 3)--Min(1)--Max(65535)
4 PPPoE Session Timeout (0 = no timeout) ----Units(mS)--Default(0)--Min(0)
4 Reserved"
		::=  {  ucOltPppoeParaEntry  3  }


	ucPppoeEntrys	OBJECT-TYPE	
		SYNTAX			DisplayString  ( SIZE ( 0 .. 255  ) ) 
		MAX-ACCESS		read-only
		STATUS			current
		DESCRIPTION		"Size    Description
10 OLT Logical Link Label
    Entry 0 Data
6  Entry 0 PPPoE Client MAC Addr
2  Entry 0 PPPoE Session Id
2  Entry 0 VID - Network VLan Id
   ...
    Entry N - 1 Data"
		::=  {  ucOltPppoeParaEntry  4  }


	ucPppoeOperatin	OBJECT-TYPE	
		SYNTAX			INTEGER  { nop ( 0 ) , delete ( 1 ) } 
		MAX-ACCESS		read-write
		STATUS			current
		DESCRIPTION		"Description"
		::=  {  ucOltPppoeParaEntry  5  }

	ucLLIDPppoeEntryTable	OBJECT-TYPE
		SYNTAX		SEQUENCE  OF  UcLLIDPppoeEntryEntry
		MAX-ACCESS	not-accessible
		STATUS		current
		DESCRIPTION	"Description"
		::=  { ucAuthentication  2 }

	ucLLIDPppoeEntryEntry	OBJECT-TYPE
		SYNTAX		UcLLIDPppoeEntryEntry
		MAX-ACCESS	not-accessible
		STATUS		current
		DESCRIPTION	"Description"
		INDEX		{  ucLLIDPppoeSlotIndex, ucLLIDPppoePonIndex, ucLLIDPppoeOnuIndex, ucLLIDPppoeLLIDIndex  }
		::=  { ucLLIDPppoeEntryTable 1 }

	UcLLIDPppoeEntryEntry  ::=  SEQUENCE {
		ucLLIDPppoeSlotIndex  Integer32,
		ucLLIDPppoePonIndex  Integer32,
		ucLLIDPppoeOnuIndex  INTEGER,
		ucLLIDPppoeLLIDIndex  Integer32,
		ucLLIDPppoeEntrys  DisplayString,
		ucLLIDPppoeOperation  INTEGER
		}


	ucLLIDPppoeSlotIndex	OBJECT-TYPE	
		SYNTAX			Integer32  ( 1 .. 16  ) 
		MAX-ACCESS		read-only
		STATUS			current
		DESCRIPTION		"Description."
		::=  {  ucLLIDPppoeEntryEntry  1  }


	ucLLIDPppoePonIndex	OBJECT-TYPE	
		SYNTAX			Integer32  ( 1 .. 32  ) 
		MAX-ACCESS		read-only
		STATUS			current
		DESCRIPTION		"Description."
		::=  {  ucLLIDPppoeEntryEntry  2  }


	ucLLIDPppoeOnuIndex	OBJECT-TYPE	
		SYNTAX			INTEGER  { none ( 1 ) , clearAllByLLID ( 2 ) } 
		MAX-ACCESS		not-accessible
		STATUS			current
		DESCRIPTION		"Description."
		::=  {  ucLLIDPppoeEntryEntry  3  }


	ucLLIDPppoeLLIDIndex	OBJECT-TYPE	
		SYNTAX			Integer32  ( -2147483648 .. 2147483647  ) 
		MAX-ACCESS		not-accessible
		STATUS			current
		DESCRIPTION		"Description"
		::=  {  ucLLIDPppoeEntryEntry  4  }


	ucLLIDPppoeEntrys	OBJECT-TYPE	
		SYNTAX			DisplayString
		MAX-ACCESS		read-only
		STATUS			current
		DESCRIPTION		"Size    Description
   Entry 0 Data
6 Entry 0 PPPoE Client MAC Addr
2 Entry 0 PPPoE Session Id
2 Entry 0 VID - Network VLan Id
   ...
   Entry N - 1 Data"
		::=  {  ucLLIDPppoeEntryEntry  5  }


	ucLLIDPppoeOperation	OBJECT-TYPE	
		SYNTAX			INTEGER  { nop ( 0 ) , delete ( 1 ) } 
		MAX-ACCESS		read-write
		STATUS			current
		DESCRIPTION		"Description"
		::=  {  ucLLIDPppoeEntryEntry  6  }

	ucAuthLinkTable	OBJECT-TYPE
		SYNTAX		SEQUENCE  OF  UcAuthLinkEntry
		MAX-ACCESS	not-accessible
		STATUS		current
		DESCRIPTION	"Description"
		::=  { ucAuthentication  3 }

	ucAuthLinkEntry	OBJECT-TYPE
		SYNTAX		UcAuthLinkEntry
		MAX-ACCESS	not-accessible
		STATUS		current
		DESCRIPTION	"Description"
		INDEX		{  ucAuthLinkSlotIndex, ucAuthLinkPonIndex, ucAuthLinkOnuIndex, ucAuthLinkLLIDIndex  }
		::=  { ucAuthLinkTable 1 }

	UcAuthLinkEntry  ::=  SEQUENCE {
		ucAuthLinkSlotIndex  Integer32,
		ucAuthLinkPonIndex  Integer32,
		ucAuthLinkOnuIndex  Integer32,
		ucAuthLinkLLIDIndex  Integer32,
		ucAuthLinkLLID  OCTET STRING,
		ucAuthLinkState  INTEGER,
		ucAuthLinkOperation  INTEGER,
		ucAuthLinkLLIDAsigned  Integer32,
		ucLLIDSLADownstream  DisplayString,
		ucLLIDSLAUpstream  DisplayString,
		ucLLIDMulticastSLA  DisplayString,
		ucLLIDSLAWeightDownstream  DisplayString,
		ucLLIDSLAWeightUpstream  DisplayString,
		ucLLIDSLADelete  DisplayString,
		ucLLIDMulticastSLADelete  DisplayString,
		ucAuthLinkName  DisplayString,
		ucLLIDADDStaticBridgingEntry  DisplayString
		}


	ucAuthLinkSlotIndex	OBJECT-TYPE	
		SYNTAX			Integer32  ( 1 .. 16  ) 
		MAX-ACCESS		read-only
		STATUS			current
		DESCRIPTION		"Description."
		::=  {  ucAuthLinkEntry  1  }


	ucAuthLinkPonIndex	OBJECT-TYPE	
		SYNTAX			Integer32  ( 1 .. 32  ) 
		MAX-ACCESS		read-only
		STATUS			current
		DESCRIPTION		"Description."
		::=  {  ucAuthLinkEntry  2  }


	ucAuthLinkOnuIndex	OBJECT-TYPE	
		SYNTAX			Integer32  ( 1 .. 256  ) 
		MAX-ACCESS		read-only
		STATUS			current
		DESCRIPTION		"Description."
		::=  {  ucAuthLinkEntry  3  }


	ucAuthLinkLLIDIndex	OBJECT-TYPE	
		SYNTAX			Integer32  ( 1 .. 32  ) 
		MAX-ACCESS		read-only
		STATUS			current
		DESCRIPTION		"Description."
		::=  {  ucAuthLinkEntry  4  }


	ucAuthLinkLLID	OBJECT-TYPE	
		SYNTAX			OCTET STRING
		MAX-ACCESS		read-only
		STATUS			current
		DESCRIPTION		"Description."
		::=  {  ucAuthLinkEntry  5  }


	ucAuthLinkState	OBJECT-TYPE	
		SYNTAX			INTEGER  { linkinvalid ( 0 ) , linkknownlink ( 1 ) , linkdiscovered ( 2 ) , linkblocked ( 3 ) } 
		MAX-ACCESS		read-only
		STATUS			current
		DESCRIPTION		"Description."
		::=  {  ucAuthLinkEntry  6  }


	ucAuthLinkOperation	OBJECT-TYPE	
		SYNTAX			INTEGER  { nop ( 0 ) , block ( 1 ) , unblock ( 2 ) , rediscovery ( 3 ) , clearAllProvision ( 4 ) , clearAllKnownLink ( 5 ) } 
		MAX-ACCESS		read-write
		STATUS			current
		DESCRIPTION		"Description."
		::=  {  ucAuthLinkEntry  7  }


	ucAuthLinkLLIDAsigned	OBJECT-TYPE	
		SYNTAX			Integer32  ( 0 .. 65535  ) 
		MAX-ACCESS		read-only
		STATUS			current
		DESCRIPTION		"Description."
		::=  {  ucAuthLinkEntry  8  }


	ucLLIDSLADownstream	OBJECT-TYPE	
		SYNTAX			DisplayString  ( SIZE ( 0 .. 255  ) ) 
		MAX-ACCESS		read-write
		STATUS			current
		DESCRIPTION		"Size    Description
10 Queue Label(6:mac,2:port,2:queueNum)
1 Direction (1 =Downstream, 0 =Upstream)
4 Minimum Guaranteed Bandwidth ----Units(Kbps)--Default(100,000)--Min(256)--Max(1,000,000)
4 Maximum Allowed Bandwidth ----Units(Kbps)--Default(100,000)--Min(256(0 = Best Effort))--Max(1,000,000)
2 Delay Sensitive(0: Tolerant,1: Sensitive)----Default(0)
2 Max Burst Size ----Units(KBytes)--Default(100)--Min(1)--Max(256)
4 TDM Rate 250 ----Units(us)--Default(0)--Min(1)--Max(4000)
4 TDM Grant Length ----Units(Byte)--Default(0)--Min(84)--Max(131072)
2 Reserved 0
1 SLA State (Enabled = 1,Disabled = 0). This is included only in the Get SLA reply.


Note that hardware limits the accuracy of these values. Provisioned values will be rounded up by the firmware to
the next larger physically available increment. In addition, an additional 200 ppm may be added by the firmware
to the provisioned bandwidth to allow for permissible clock frequency differences between ONU and OLT. With
the TK3721, shaping is accurate to within 1% of the provisioned bandwidth values, and the maximum burst
allowed is accurate to within 5% of the maximum size. The minimum non-zero value that can be provisioned for
bandwidth values is 256Kbps. In addition, when setting an SLA where the Max Allowed BW > Min Guaranteed
BW, the difference must be 256Kbps or greater."
		::=  {  ucAuthLinkEntry  9  }


	ucLLIDSLAUpstream	OBJECT-TYPE	
		SYNTAX			DisplayString  ( SIZE ( 0 .. 255  ) ) 
		MAX-ACCESS		read-write
		STATUS			current
		DESCRIPTION		"Size    Description
10 Queue Label(6:mac,2:port,2:queueNum)
1 Direction (1 =Downstream, 0 =Upstream)
4 Minimum Guaranteed Bandwidth ----Units(Kbps)--Default(100,000)--Min(256)--Max(1,000,000)
4 Maximum Allowed Bandwidth ----Units(Kbps)--Default(100,000)--Min(256(0 = Best Effort))--Max(1,000,000)
2 Delay Sensitive(0: Tolerant,1: Sensitive)----Default(0)
2 Max Burst Size ----Units(KBytes)--Default(100)--Min(1)--Max(256)
4 TDM Rate 250 ----Units(us)--Default(0)--Min(1)--Max(4000)
4 TDM Grant Length ----Units(Byte)--Default(0)--Min(84)--Max(131072)
2 Reserved 0
1 SLA State (Enabled = 1,Disabled = 0). This is included only in the Get SLA reply.


Note that hardware limits the accuracy of these values. Provisioned values will be rounded up by the firmware to
the next larger physically available increment. In addition, an additional 200 ppm may be added by the firmware
to the provisioned bandwidth to allow for permissible clock frequency differences between ONU and OLT. With
the TK3721, shaping is accurate to within 1% of the provisioned bandwidth values, and the maximum burst
allowed is accurate to within 5% of the maximum size. The minimum non-zero value that can be provisioned for
bandwidth values is 256Kbps. In addition, when setting an SLA where the Max Allowed BW > Min Guaranteed
BW, the difference must be 256Kbps or greater."
		::=  {  ucAuthLinkEntry  10  }


	ucLLIDMulticastSLA	OBJECT-TYPE	
		SYNTAX			DisplayString  ( SIZE ( 0 .. 255  ) ) 
		MAX-ACCESS		read-write
		STATUS			current
		DESCRIPTION		"Size    Description
10 Queue Label(6:mac,2:port,2:queueNum)
4 Minimum Guaranteed Bandwidth ----Units(Kbps)--Default(100,000)--Min(256)--Max(1,000,000)
4 Maximum Allowed Bandwidth ----Units(Kbps)--Default(100,000)--Min(256(0 = Best Effort))--Max(1,000,000)
2 Priority Level(0: Tolerant,1: Sensitive)----Default(0)
2 Max Burst Size ----Units(KBytes)--Default(100)--Min(1)--Max(256)
4 TDM Rate 250 ----Units(us)--Default(0)--Min(1)--Max(4000)
4 TDM Grant Length ----Units(Byte)--Default(0)--Min(84)--Max(131072)
2 Reserved 0
1 SLA State (Enabled = 1,Disabled = 0). This is included only in the Get SLA reply.


Note that hardware limits the accuracy of these values. Provisioned values will be rounded up by the firmware to
the next larger physically available increment. In addition, an additional 200 ppm may be added by the firmware
to the provisioned bandwidth to allow for permissible clock frequency differences between ONU and OLT. With
the TK3721, shaping is accurate to within 1% of the provisioned bandwidth values, and the maximum burst
allowed is accurate to within 5% of the maximum size. The minimum non-zero value that can be provisioned for
bandwidth values is 256Kbps. In addition, when setting an SLA where the Max Allowed BW > Min Guaranteed
BW, the difference must be 256Kbps or greater."
		::=  {  ucAuthLinkEntry  11  }


	ucLLIDSLAWeightDownstream	OBJECT-TYPE	
		SYNTAX			DisplayString  ( SIZE ( 0 .. 255  ) ) 
		MAX-ACCESS		read-write
		STATUS			current
		DESCRIPTION		"Size    Description
10 Logical Link Label
1 Direction:(1 = Downstream, 0 = Upstream)
2 DBA Tokens (set to zero to restore defaults) ----Units(Kbytes)--Default(4)--Min(0)--Max(255)
2 Scheduler Min-tokens (set to zero to restore defaults) ----Units(Kbytes)--Default(2)--Min(0)--Max(511)
2 Scheduler Max-tokens (set to zero to restore defaults)----Units(Kbytes)--Default(2)--Min(0)--Max(511)


The link and queue schedulers in the TK3721 use a weighted priority-based round-robin discipline. In general the
appropriate values of priority and weight for a link are selected by the firmware when an SLA is specified. This
command provides a low-level control for setting the upstream and downstream weights on a per-link basis. It is
recommended that the Host use the default settings as far as possible."
		::=  {  ucAuthLinkEntry  12  }


	ucLLIDSLAWeightUpstream	OBJECT-TYPE	
		SYNTAX			DisplayString
		MAX-ACCESS		read-write
		STATUS			current
		DESCRIPTION		"Size    Description
10 Logical Link Label
1 Direction:(1 = Downstream, 0 = Upstream)
2 DBA Tokens (set to zero to restore defaults) ----Units(Kbytes)--Default(4)--Min(0)--Max(255)
2 Scheduler Min-tokens (set to zero to restore defaults) ----Units(Kbytes)--Default(2)--Min(0)--Max(511)
2 Scheduler Max-tokens (set to zero to restore defaults)----Units(Kbytes)--Default(2)--Min(0)--Max(511)


The link and queue schedulers in the TK3721 use a weighted priority-based round-robin discipline. In general the
appropriate values of priority and weight for a link are selected by the firmware when an SLA is specified. This
command provides a low-level control for setting the upstream and downstream weights on a per-link basis. It is
recommended that the Host use the default settings as far as possible."
		::=  {  ucAuthLinkEntry  13  }


	ucLLIDSLADelete	OBJECT-TYPE	
		SYNTAX			DisplayString  ( SIZE ( 0 .. 255  ) ) 
		MAX-ACCESS		read-write
		STATUS			current
		DESCRIPTION		"Size    Description
10 Queue Label(6:mac,2:port,2:queueNum)
1 Direction (1 = Downstream, 0 = Upstream)"
		::=  {  ucAuthLinkEntry  14  }


	ucLLIDMulticastSLADelete	OBJECT-TYPE	
		SYNTAX			DisplayString  ( SIZE ( 0 .. 255  ) ) 
		MAX-ACCESS		read-write
		STATUS			current
		DESCRIPTION		"Size    Description
10 Queue Label(6:mac,2:port,2:queueNum)"
		::=  {  ucAuthLinkEntry  15  }


	ucAuthLinkName	OBJECT-TYPE	
		SYNTAX			DisplayString  ( SIZE ( 0 .. 32  ) ) 
		MAX-ACCESS		read-write
		STATUS			current
		DESCRIPTION		"Description"
		::=  {  ucAuthLinkEntry  16  }


	ucLLIDADDStaticBridgingEntry	OBJECT-TYPE	
		SYNTAX			DisplayString  ( SIZE ( 0 .. 255  ) ) 
		MAX-ACCESS		read-write
		STATUS			current
		DESCRIPTION		"Size    Description
1 Operation(0=Nop,1=Add,2=Delete)
2 Number Mac Address
6     Downstream destination MAC Address of bridged frame"
		::=  {  ucAuthLinkEntry  17  }

	ucDhcpParaTable	OBJECT-TYPE
		SYNTAX		SEQUENCE  OF  UcDhcpParaEntry
		MAX-ACCESS	not-accessible
		STATUS		current
		DESCRIPTION	"Description"
		::=  { ucLayer3  1 }

	ucDhcpParaEntry	OBJECT-TYPE
		SYNTAX		UcDhcpParaEntry
		MAX-ACCESS	not-accessible
		STATUS		current
		DESCRIPTION	"Description"
		INDEX		{  ucDhcpParaSlotIndex  }
		::=  { ucDhcpParaTable 1 }

	UcDhcpParaEntry  ::=  SEQUENCE {
		ucDhcpParaSlotIndex  Integer32,
		ucDhcpParaCtrl  DisplayString
		}


	ucDhcpParaSlotIndex	OBJECT-TYPE	
		SYNTAX			Integer32  ( 1 .. 16  ) 
		MAX-ACCESS		read-only
		STATUS			current
		DESCRIPTION		"Description."
		::=  {  ucDhcpParaEntry  1  }


	ucDhcpParaCtrl	OBJECT-TYPE	
		SYNTAX			DisplayString
		MAX-ACCESS		read-write
		STATUS			current
		DESCRIPTION		"Size    Description
2 Layer 3 Mode Bits (0 = All L3 features Disabled)----Default(0x0000)(
   Bit0: DHCP Snooping Enable
   Bit1: DHCP IP / MAC Address Learning Enable
   Bit2: DHCP Relay Agent (insert Option 82 if prov'd)
   Bit3: DHCP Relay Agent Set giaddr
   Bit4: Insert Opt 82 for Unicast DHCP Requests also
   Bit5: Trust Other DHCP Relay Agent
   Bit6: ARP Snooping Enable (Needs DHCP IP Learning)
   Bit7: ARP Mode (0 = Directed ARP, 1 =ARP Proxy)
   Bit8: RARP Snooping Enable
   Bit9: RARP Mode (0=Directed RARP, 1=RARP Proxy)
   Bit10: Disable Upstream ARP Request validation
   Bit11: Disable Downstream ARP Reply validation
   Bit12: Disable Upstream ARP Reply validation
   Bit13: Exclude UDP multicast IP fragments
   Bit14: Validate IP Checksum on received frames
   Bit15: Validate UDP Checksum on received frames)
2 Maximum Number of Learned IP Addresses ----Default(0)--Min(0)--Max(3839)
2 DHCP Timer Interval ----Units(Seconds)--Default(10)--Min(1)--Max(65535)
2 DHCP Response Timer Ticks (DHCP Timer Intervals) ----Units(Ticks)--Default(3)--Min(1)--Max(65535)
2 ARP Retry Ticks (for Static IP ARPs sent to client) ----Units(Ticks)
4 DHCP Relay Agent IP SA ----Default(0)
4 Maximum DHCP Lease Time ----Units(Seconds)--Default(0)--Min(0)--Max(2 ^ 32)
4 Reserved"
		::=  {  ucDhcpParaEntry  2  }

	ucStaticIpTable	OBJECT-TYPE
		SYNTAX		SEQUENCE  OF  UcStaticIpEntry
		MAX-ACCESS	not-accessible
		STATUS		current
		DESCRIPTION	"Description"
		::=  { ucLayer3  2 }

	ucStaticIpEntry	OBJECT-TYPE
		SYNTAX		UcStaticIpEntry
		MAX-ACCESS	not-accessible
		STATUS		current
		DESCRIPTION	"Description"
		INDEX		{  ucStaticIpSlotIndex, ucStaticIpPonIndex, ucStaticIpOLTLLID  }
		::=  { ucStaticIpTable 1 }

	UcStaticIpEntry  ::=  SEQUENCE {
		ucStaticIpSlotIndex  Integer32,
		ucStaticIpPonIndex  Integer32,
		ucStaticIpOLTLLID  OCTET STRING,
		ucStaticIpStaticIp  IpAddress,
		ucStaticIpNetworkVID  Integer32,
		ucStaticIpOperation  INTEGER
		}


	ucStaticIpSlotIndex	OBJECT-TYPE	
		SYNTAX			Integer32  ( 1 .. 16  ) 
		MAX-ACCESS		read-only
		STATUS			current
		DESCRIPTION		"Description."
		::=  {  ucStaticIpEntry  1  }


	ucStaticIpPonIndex	OBJECT-TYPE	
		SYNTAX			Integer32  ( 1 .. 32  ) 
		MAX-ACCESS		read-only
		STATUS			current
		DESCRIPTION		"Description."
		::=  {  ucStaticIpEntry  2  }


	ucStaticIpOLTLLID	OBJECT-TYPE	
		SYNTAX			OCTET STRING
		MAX-ACCESS		read-only
		STATUS			current
		DESCRIPTION		"Description."
		::=  {  ucStaticIpEntry  3  }


	ucStaticIpStaticIp	OBJECT-TYPE	
		SYNTAX			IpAddress
		MAX-ACCESS		read-write
		STATUS			current
		DESCRIPTION		"Description."
		::=  {  ucStaticIpEntry  4  }


	ucStaticIpNetworkVID	OBJECT-TYPE	
		SYNTAX			Integer32  ( 0 .. 4095  ) 
		MAX-ACCESS		read-write
		STATUS			current
		DESCRIPTION		"Description."
		::=  {  ucStaticIpEntry  5  }


	ucStaticIpOperation	OBJECT-TYPE	
		SYNTAX			INTEGER  { none ( 1 ) , delete ( 2 ) } 
		MAX-ACCESS		read-write
		STATUS			current
		DESCRIPTION		"Description."
		::=  {  ucStaticIpEntry  6  }

	ucIpMacVidTable	OBJECT-TYPE
		SYNTAX		SEQUENCE  OF  UcIpMacVidEntry
		MAX-ACCESS	not-accessible
		STATUS		current
		DESCRIPTION	"Description"
		::=  { ucLayer3  3 }

	ucIpMacVidEntry	OBJECT-TYPE
		SYNTAX		UcIpMacVidEntry
		MAX-ACCESS	not-accessible
		STATUS		current
		DESCRIPTION	"Description"
		INDEX		{  ucIpMacVidSlotIndex, ucIpMacVidPonIndex, ucIpMacVidEntryIndex  }
		::=  { ucIpMacVidTable 1 }

	UcIpMacVidEntry  ::=  SEQUENCE {
		ucIpMacVidSlotIndex  Integer32,
		ucIpMacVidPonIndex  Integer32,
		ucIpMacVidOLTLLID  DisplayString,
		ucIpMacVidStatus  INTEGER,
		ucIpMacVidEntryIndex  Integer32,
		ucIpMacVidIp  IpAddress,
		ucIpMacVidMAC  DisplayString,
		ucIpMacVidNetworkVID  Integer32,
		ucIpMacVidLeaseTime  Counter32,
		ucIpMacVidLeaseAge  Counter32,
		ucIpMacVidOperation  INTEGER
		}


	ucIpMacVidSlotIndex	OBJECT-TYPE	
		SYNTAX			Integer32  ( 1 .. 16  ) 
		MAX-ACCESS		read-only
		STATUS			current
		DESCRIPTION		"Description."
		::=  {  ucIpMacVidEntry  1  }


	ucIpMacVidPonIndex	OBJECT-TYPE	
		SYNTAX			Integer32  ( 1 .. 32  ) 
		MAX-ACCESS		read-only
		STATUS			current
		DESCRIPTION		"Description."
		::=  {  ucIpMacVidEntry  2  }


	ucIpMacVidOLTLLID	OBJECT-TYPE	
		SYNTAX			DisplayString  ( SIZE ( 12 .. 12  ) ) 
		MAX-ACCESS		read-only
		STATUS			current
		DESCRIPTION		"Description."
		::=  {  ucIpMacVidEntry  3  }


	ucIpMacVidStatus	OBJECT-TYPE	
		SYNTAX			INTEGER  { dynamic ( 1 ) , static ( 2 ) } 
		MAX-ACCESS		read-write
		STATUS			current
		DESCRIPTION		"Description."
		::=  {  ucIpMacVidEntry  4  }


	ucIpMacVidEntryIndex	OBJECT-TYPE	
		SYNTAX			Integer32  ( 1 .. 65535  ) 
		MAX-ACCESS		read-only
		STATUS			current
		DESCRIPTION		"Description."
		::=  {  ucIpMacVidEntry  5  }


	ucIpMacVidIp	OBJECT-TYPE	
		SYNTAX			IpAddress
		MAX-ACCESS		read-write
		STATUS			current
		DESCRIPTION		"Description."
		::=  {  ucIpMacVidEntry  6  }


	ucIpMacVidMAC	OBJECT-TYPE	
		SYNTAX			DisplayString  ( SIZE ( 12 .. 12  ) ) 
		MAX-ACCESS		read-write
		STATUS			current
		DESCRIPTION		"Description."
		::=  {  ucIpMacVidEntry  7  }


	ucIpMacVidNetworkVID	OBJECT-TYPE	
		SYNTAX			Integer32  ( 0 .. 4095  ) 
		MAX-ACCESS		read-write
		STATUS			current
		DESCRIPTION		"Description."
		::=  {  ucIpMacVidEntry  8  }


	ucIpMacVidLeaseTime	OBJECT-TYPE	
		SYNTAX			Counter32
		MAX-ACCESS		read-write
		STATUS			current
		DESCRIPTION		"Description."
		::=  {  ucIpMacVidEntry  9  }


	ucIpMacVidLeaseAge	OBJECT-TYPE	
		SYNTAX			Counter32
		MAX-ACCESS		read-only
		STATUS			current
		DESCRIPTION		"Description."
		::=  {  ucIpMacVidEntry  10  }


	ucIpMacVidOperation	OBJECT-TYPE	
		SYNTAX			INTEGER  { none ( 1 ) , add ( 2 ) , clearAllOnLLID ( 3 ) } 
		MAX-ACCESS		read-write
		STATUS			current
		DESCRIPTION		"Description."
		::=  {  ucIpMacVidEntry  11  }

	ucLLIDDhcpOpt82Table	OBJECT-TYPE
		SYNTAX		SEQUENCE  OF  UcLLIDDhcpOpt82Entry
		MAX-ACCESS	not-accessible
		STATUS		current
		DESCRIPTION	"When Layer 3 Switching is enabled, the OLT can be configured to act as a DHCP Relay
 Agent. The agent intercepts DHCP packets in both directions, adding option 82 fields in
 the upstream and stripping option 82 fields in the downstream. The Layer 3 Switching
OLT feature is enabled via the Get / Set Olt Switching Mode command.
The Host enables DHCP Relay Agent functionality per link by defining the option 82 data
 the OLT will add in the upstream direction for each link. The data is opaque to the OLT;
 its format is completely up to the Host to decide.
The OLT simply takes the sequence of bytes given by the length and value fields (see
 table below) and adds it to the upstream DHCP packets on the link. The Relay Agent
 feature (Option 82 stuffing) is disabled per link by setting the length field to zero. (There
 is no value field in a message with length of zero.)"
		::=  { ucLayer3  4 }

	ucLLIDDhcpOpt82Entry	OBJECT-TYPE
		SYNTAX		UcLLIDDhcpOpt82Entry
		MAX-ACCESS	not-accessible
		STATUS		current
		DESCRIPTION	"Row Description"
		INDEX		{  ucLLIDDhcpOpt82SlotIndex, ucLLIDDhcpOpt82PonIndex, ucLLIDDhcpOpt82OnuIndex, ucLLIDDhcpOpt82LLIDIndex  }
		::=  { ucLLIDDhcpOpt82Table 1 }

	UcLLIDDhcpOpt82Entry  ::=  SEQUENCE {
		ucLLIDDhcpOpt82SlotIndex  Integer32,
		ucLLIDDhcpOpt82PonIndex  Integer32,
		ucLLIDDhcpOpt82OnuIndex  Integer32,
		ucLLIDDhcpOpt82LLIDIndex  Integer32,
		ucLLIDDhcpOpt82Ctrl  DisplayString
		}


	ucLLIDDhcpOpt82SlotIndex	OBJECT-TYPE	
		SYNTAX			Integer32  ( 1 .. 16  ) 
		MAX-ACCESS		read-only
		STATUS			current
		DESCRIPTION		"Column Description"
		::=  {  ucLLIDDhcpOpt82Entry  1  }


	ucLLIDDhcpOpt82PonIndex	OBJECT-TYPE	
		SYNTAX			Integer32  ( 1 .. 32  ) 
		MAX-ACCESS		not-accessible
		STATUS			current
		DESCRIPTION		"Column Description"
		::=  {  ucLLIDDhcpOpt82Entry  2  }


	ucLLIDDhcpOpt82OnuIndex	OBJECT-TYPE	
		SYNTAX			Integer32
		MAX-ACCESS		not-accessible
		STATUS			current
		DESCRIPTION		"Column Description"
		::=  {  ucLLIDDhcpOpt82Entry  3  }


	ucLLIDDhcpOpt82LLIDIndex	OBJECT-TYPE	
		SYNTAX			Integer32  ( 1 .. 64  ) 
		MAX-ACCESS		not-accessible
		STATUS			current
		DESCRIPTION		"Column Description"
		::=  {  ucLLIDDhcpOpt82Entry  4  }


	ucLLIDDhcpOpt82Ctrl	OBJECT-TYPE	
		SYNTAX			DisplayString
		MAX-ACCESS		read-write
		STATUS			current
		DESCRIPTION		"Size    Description
10 OLT Logical Link Label
1 Option 82 length (length of the value field below) ----Units(octets)--Min(0)--Max(64)
N Option 82 value. Length bytes of arbitrary binary data."
		::=  {  ucLLIDDhcpOpt82Entry  5  }

	ucOnuRstpCtrlTable	OBJECT-TYPE
		SYNTAX		SEQUENCE  OF  UcOnuRstpCtrlEntry
		MAX-ACCESS	not-accessible
		STATUS		current
		DESCRIPTION	"Description"
		::=  { ucSTP  1 }

	ucOnuRstpCtrlEntry	OBJECT-TYPE
		SYNTAX		UcOnuRstpCtrlEntry
		MAX-ACCESS	not-accessible
		STATUS		current
		DESCRIPTION	"Description"
		INDEX		{  ucOnuRstpCtrlSlotIndex, ucOnuRstpCtrlPonIndex, ucOnuRstpCtrlOnuIndex  }
		::=  { ucOnuRstpCtrlTable 1 }

	UcOnuRstpCtrlEntry  ::=  SEQUENCE {
		ucOnuRstpCtrlSlotIndex  Integer32,
		ucOnuRstpCtrlPonIndex  Integer32,
		ucOnuRstpCtrlOnuIndex  Integer32,
		ucOnuRstpCtrl  DisplayString
		}


	ucOnuRstpCtrlSlotIndex	OBJECT-TYPE	
		SYNTAX			Integer32  ( 1 .. 16  ) 
		MAX-ACCESS		read-only
		STATUS			current
		DESCRIPTION		"Description."
		::=  {  ucOnuRstpCtrlEntry  1  }


	ucOnuRstpCtrlPonIndex	OBJECT-TYPE	
		SYNTAX			Integer32  ( 1 .. 32  ) 
		MAX-ACCESS		read-only
		STATUS			current
		DESCRIPTION		"Description."
		::=  {  ucOnuRstpCtrlEntry  2  }


	ucOnuRstpCtrlOnuIndex	OBJECT-TYPE	
		SYNTAX			Integer32  ( 1 .. 256  ) 
		MAX-ACCESS		read-only
		STATUS			current
		DESCRIPTION		"Description."
		::=  {  ucOnuRstpCtrlEntry  3  }


	ucOnuRstpCtrl	OBJECT-TYPE	
		SYNTAX			DisplayString  ( SIZE ( 35 .. 131  ) ) 
		MAX-ACCESS		read-write
		STATUS			current
		DESCRIPTION		"Size    Description
2 Bridge priority----Default(32768)--Min(0)--Max(0xFFFF)
1 RSTP Bridge Mode(0: Disabled,1: Passthrough,2: Enabled)----Default(0)--Min(0)--Max(3)
1 RSTP Options Bitmap (reserved for future use)
2 Maximum age when root----Units(10 msec)--Default(2000)--Min(600)--Max(4000)
2 Hello time when root ----Units(10 msec)--Default(200)--Min(See Note)--Max(See Note)
2 Forward delay when root ----Units(10 msec)--Default(1500)--Min(400)--Max(3000)
1 Number of Ports
1       Reserved for future use
1       Port priority--Default(128)--Min(0)--Max(255)
4       Path cost --Default(0)--Min(0)--Max(0xFFFFFFFF)


Note: As per Section 17.14 of IEEE 802.1D-2004, the firmware doesn't set restrictions on minimum and
maximum values for the Hello Time."
		::=  {  ucOnuRstpCtrlEntry  4  }

	ucOnuRstpStatusTable	OBJECT-TYPE
		SYNTAX		SEQUENCE  OF  UcOnuRstpStatusEntry
		MAX-ACCESS	not-accessible
		STATUS		current
		DESCRIPTION	"Description"
		::=  { ucSTP  2 }

	ucOnuRstpStatusEntry	OBJECT-TYPE
		SYNTAX		UcOnuRstpStatusEntry
		MAX-ACCESS	not-accessible
		STATUS		current
		DESCRIPTION	"Description"
		INDEX		{  ucOnuRstpStatusSlotIndex, ucOnuRstpStatusPonIndex, ucOnuRstpStatusOnuIndex  }
		::=  { ucOnuRstpStatusTable 1 }

	UcOnuRstpStatusEntry  ::=  SEQUENCE {
		ucOnuRstpStatusSlotIndex  Integer32,
		ucOnuRstpStatusPonIndex  Integer32,
		ucOnuRstpStatusOnuIndex  Integer32,
		ucOnuRstpStatus  DisplayString
		}


	ucOnuRstpStatusSlotIndex	OBJECT-TYPE	
		SYNTAX			Integer32  ( 1 .. 16  ) 
		MAX-ACCESS		read-only
		STATUS			current
		DESCRIPTION		"Description."
		::=  {  ucOnuRstpStatusEntry  1  }


	ucOnuRstpStatusPonIndex	OBJECT-TYPE	
		SYNTAX			Integer32  ( 1 .. 32  ) 
		MAX-ACCESS		read-only
		STATUS			current
		DESCRIPTION		"Description."
		::=  {  ucOnuRstpStatusEntry  2  }


	ucOnuRstpStatusOnuIndex	OBJECT-TYPE	
		SYNTAX			Integer32  ( 1 .. 256  ) 
		MAX-ACCESS		read-only
		STATUS			current
		DESCRIPTION		"Description."
		::=  {  ucOnuRstpStatusEntry  3  }


	ucOnuRstpStatus	OBJECT-TYPE	
		SYNTAX			DisplayString  ( SIZE ( 121 .. 581  ) ) 
		MAX-ACCESS		read-only
		STATUS			current
		DESCRIPTION		"Size    Description
4 Time since topology change ----Units(10 ms)--Min(0)--Max(0xFFFFFFFF)
4 Topology changes since last reset----Default(0)--Min(0)--Max(0xFFFFFFFF)
8 Designated root id (priority + MAC address)
2 Root cost ----Default(0)--Min(0)--Max(0xFFFF)
2 Root port number ----Min(0)--Max(0xFFFF)
2 Maximum age ----Units(10 ms)--Min(0)--Max(0xFFFF)
2 Hello Count ----Units(10 ms)--Min(0)--Max(0xFFFF)
2 Forward delay ----Units(10 ms)--Min(0)--Max(0xFFFF)
2 Hold Count ----Min(0)--Max(0xFF)
1 Number of ports
1     Port current state(1: Disabled,2: Blocking,3: Listening,4: Learning,5: Forwarding,6: Broken) ----Default(1)--Min(1)--Max(6)
8     Designated root id
2     Designated cost ----Min(0)--Max(0xFFFF)
8     Designated bridge id
2     Designated port
2     Forward transitions ----Min(0)--Max(0xFFFF)"
		::=  {  ucOnuRstpStatusEntry  4  }

	ucOltTrap	OBJECT-IDENTITY
		STATUS			current
		DESCRIPTION		"Description."
		::=  {  ucPonTrap  1  }

	ucOltPortTrap	OBJECT-IDENTITY
		STATUS			current
		DESCRIPTION		"Description."
		::=  {  ucPonTrap  2  }

	ucOltLLIDTrap	OBJECT-IDENTITY
		STATUS			current
		DESCRIPTION		"Description."
		::=  {  ucPonTrap  3  }

	ucOnuTrap	OBJECT-IDENTITY
		STATUS			current
		DESCRIPTION		"Description."
		::=  {  ucPonTrap  4  }

	ucOnuPortTrap	OBJECT-IDENTITY
		STATUS			current
		DESCRIPTION		"Description."
		::=  {  ucPonTrap  5  }

	ucOnuLLIDTrap	OBJECT-IDENTITY
		STATUS			current
		DESCRIPTION		"Description."
		::=  {  ucPonTrap  6  }

	ucOltCmdTrap	OBJECT-IDENTITY
		STATUS			current
		DESCRIPTION		"Description."
		::=  {  ucPonTrap  7  }

	ucMemOltTable	OBJECT-TYPE
		SYNTAX		SEQUENCE  OF  UcMemOltEntry
		MAX-ACCESS	not-accessible
		STATUS		current
		DESCRIPTION	"Description."
		::=  { ucNMS  1 }

	ucMemOltEntry	OBJECT-TYPE
		SYNTAX		UcMemOltEntry
		MAX-ACCESS	not-accessible
		STATUS		current
		DESCRIPTION	"Description"
		INDEX		{  ucMemOltSlotIndex  }
		::=  { ucMemOltTable 1 }

	UcMemOltEntry  ::=  SEQUENCE {
		ucMemOltSlotIndex  Integer32,
		ucMemOltMemOctet  OCTET STRING,
		ucMemOltMemSize  Integer32,
		ucMemOnuOctet  OCTET STRING,
		ucMemOnuOctetSize  Integer32,
		ucMemLLIDOctet  OCTET STRING,
		ucMemLLIDOctetSize  Integer32
		}


	ucMemOltSlotIndex	OBJECT-TYPE	
		SYNTAX			Integer32  ( 1 .. 16  ) 
		MAX-ACCESS		read-only
		STATUS			current
		DESCRIPTION		"DESCRIPTION"
		::=  {  ucMemOltEntry  1  }


	ucMemOltMemOctet	OBJECT-TYPE	
		SYNTAX			OCTET STRING
		MAX-ACCESS		read-only
		STATUS			current
		DESCRIPTION		"DESCRIPTION"
		::=  {  ucMemOltEntry  2  }


	ucMemOltMemSize	OBJECT-TYPE	
		SYNTAX			Integer32
		MAX-ACCESS		read-only
		STATUS			current
		DESCRIPTION		"DESCRIPTION"
		::=  {  ucMemOltEntry  3  }


	ucMemOnuOctet	OBJECT-TYPE	
		SYNTAX			OCTET STRING
		MAX-ACCESS		read-only
		STATUS			current
		DESCRIPTION		"DESCRIPTION"
		::=  {  ucMemOltEntry  4  }


	ucMemOnuOctetSize	OBJECT-TYPE	
		SYNTAX			Integer32
		MAX-ACCESS		read-only
		STATUS			current
		DESCRIPTION		"DESCRIPTION"
		::=  {  ucMemOltEntry  5  }


	ucMemLLIDOctet	OBJECT-TYPE	
		SYNTAX			OCTET STRING
		MAX-ACCESS		read-only
		STATUS			current
		DESCRIPTION		"DESCRIPTION"
		::=  {  ucMemOltEntry  6  }


	ucMemLLIDOctetSize	OBJECT-TYPE	
		SYNTAX			Integer32
		MAX-ACCESS		read-only
		STATUS			current
		DESCRIPTION		"DESCRIPTION"
		::=  {  ucMemOltEntry  7  }

	ucMemOnuTable	OBJECT-TYPE
		SYNTAX		SEQUENCE  OF  UcMemOnuEntry
		MAX-ACCESS	not-accessible
		STATUS		current
		DESCRIPTION	"Description."
		::=  { ucNMS  2 }

	ucMemOnuEntry	OBJECT-TYPE
		SYNTAX		UcMemOnuEntry
		MAX-ACCESS	not-accessible
		STATUS		current
		DESCRIPTION	"Description"
		INDEX		{  ucMemOnuSlotIndex, ucMemOnuPonIndex, ucMemOnuOnuIndex  }
		::=  { ucMemOnuTable 1 }

	UcMemOnuEntry  ::=  SEQUENCE {
		ucMemOnuSlotIndex  Integer32,
		ucMemOnuPonIndex  Integer32,
		ucMemOnuOnuIndex  Integer32,
		ucMemOnuMemOctet  OCTET STRING,
		ucMemOnuMemSize  Integer32
		}


	ucMemOnuSlotIndex	OBJECT-TYPE	
		SYNTAX			Integer32  ( 1 .. 16  ) 
		MAX-ACCESS		read-only
		STATUS			current
		DESCRIPTION		"DESCRIPTION"
		::=  {  ucMemOnuEntry  1  }


	ucMemOnuPonIndex	OBJECT-TYPE	
		SYNTAX			Integer32  ( 1 .. 32  ) 
		MAX-ACCESS		read-only
		STATUS			current
		DESCRIPTION		"DESCRIPTION"
		::=  {  ucMemOnuEntry  2  }


	ucMemOnuOnuIndex	OBJECT-TYPE	
		SYNTAX			Integer32  ( 1 .. 32  ) 
		MAX-ACCESS		read-only
		STATUS			current
		DESCRIPTION		"DESCRIPTION"
		::=  {  ucMemOnuEntry  3  }


	ucMemOnuMemOctet	OBJECT-TYPE	
		SYNTAX			OCTET STRING
		MAX-ACCESS		read-only
		STATUS			current
		DESCRIPTION		"DESCRIPTION"
		::=  {  ucMemOnuEntry  4  }


	ucMemOnuMemSize	OBJECT-TYPE	
		SYNTAX			Integer32
		MAX-ACCESS		read-only
		STATUS			current
		DESCRIPTION		"Slot index"
		::=  {  ucMemOnuEntry  5  }

	ucMemLLIDTable	OBJECT-TYPE
		SYNTAX		SEQUENCE  OF  UcMemLLIDEntry
		MAX-ACCESS	not-accessible
		STATUS		current
		DESCRIPTION	"Description."
		::=  { ucNMS  3 }

	ucMemLLIDEntry	OBJECT-TYPE
		SYNTAX		UcMemLLIDEntry
		MAX-ACCESS	not-accessible
		STATUS		current
		DESCRIPTION	"Description"
		INDEX		{  ucMemLLIDSlotIndex, ucMemLLIDPonIndex, ucMemLLIDOnuIndex, ucMemLLIDIndex  }
		::=  { ucMemLLIDTable 1 }

	UcMemLLIDEntry  ::=  SEQUENCE {
		ucMemLLIDSlotIndex  Integer32,
		ucMemLLIDPonIndex  Integer32,
		ucMemLLIDOnuIndex  Integer32,
		ucMemLLIDIndex  Integer32,
		ucMemLLIDMemOctet  OCTET STRING,
		ucMemLLIDMemSize  Integer32
		}


	ucMemLLIDSlotIndex	OBJECT-TYPE	
		SYNTAX			Integer32  ( 1 .. 16  ) 
		MAX-ACCESS		read-only
		STATUS			current
		DESCRIPTION		"DESCRIPTION"
		::=  {  ucMemLLIDEntry  1  }


	ucMemLLIDPonIndex	OBJECT-TYPE	
		SYNTAX			Integer32  ( 1 .. 32  ) 
		MAX-ACCESS		read-only
		STATUS			current
		DESCRIPTION		"DESCRIPTION"
		::=  {  ucMemLLIDEntry  2  }


	ucMemLLIDOnuIndex	OBJECT-TYPE	
		SYNTAX			Integer32  ( 1 .. 32  ) 
		MAX-ACCESS		read-only
		STATUS			current
		DESCRIPTION		"DESCRIPTION"
		::=  {  ucMemLLIDEntry  3  }


	ucMemLLIDIndex	OBJECT-TYPE	
		SYNTAX			Integer32  ( 1 .. 16  ) 
		MAX-ACCESS		read-only
		STATUS			current
		DESCRIPTION		"DESCRIPTION"
		::=  {  ucMemLLIDEntry  4  }


	ucMemLLIDMemOctet	OBJECT-TYPE	
		SYNTAX			OCTET STRING
		MAX-ACCESS		read-only
		STATUS			current
		DESCRIPTION		"DESCRIPTION"
		::=  {  ucMemLLIDEntry  5  }


	ucMemLLIDMemSize	OBJECT-TYPE	
		SYNTAX			Integer32
		MAX-ACCESS		read-only
		STATUS			current
		DESCRIPTION		"DESCRIPTION"
		::=  {  ucMemLLIDEntry  6  }

	ucChsExistTrap	NOTIFICATION-TYPE
		OBJECTS			{ ucChsExist }
		STATUS			current
		DESCRIPTION		"Description."
		::=  {  ucChassisTrapV2  1  }

	ucChsFanaTrap	NOTIFICATION-TYPE
		OBJECTS			{ ucChsFana }
		STATUS			current
		DESCRIPTION		"Description."
		::=  {  ucChassisTrapV2  2  }

	ucChsFanbTrap	NOTIFICATION-TYPE
		OBJECTS			{ ucChsFanb }
		STATUS			current
		DESCRIPTION		"Description."
		::=  {  ucChassisTrapV2  3  }

	ucChsPwaTrap	NOTIFICATION-TYPE
		OBJECTS			{ ucChsPwa }
		STATUS			current
		DESCRIPTION		"Description."
		::=  {  ucChassisTrapV2  4  }

	ucChsPwbTrap	NOTIFICATION-TYPE
		OBJECTS			{ ucChsPwb }
		STATUS			current
		DESCRIPTION		"Description."
		::=  {  ucChassisTrapV2  5  }

	ucChsTmpTrap	NOTIFICATION-TYPE
		OBJECTS			{ ucChsTmp }
		STATUS			current
		DESCRIPTION		"Description."
		::=  {  ucChassisTrapV2  6  }

	ucSlotNewCardTrap	NOTIFICATION-TYPE
		OBJECTS			{ ucSlotStatus }
		STATUS			current
		DESCRIPTION		"Description."
		::=  {  ucSlotTrapV2  1  }

	ucSlotLostCardTrap	NOTIFICATION-TYPE
		OBJECTS			{ ucSlotStatus }
		STATUS			current
		DESCRIPTION		"Description."
		::=  {  ucSlotTrapV2  2  }

	ucLogFSIntervalTime	OBJECT-TYPE	
		SYNTAX			DateAndTime
		MAX-ACCESS		read-write
		STATUS			current
		DESCRIPTION		"set the saving Logging Interval time,no less then 1 hour, count with minute"
		::=  {  ucLogfilesave  1  }

	ucLogFSEverydayTime	OBJECT-TYPE	
		SYNTAX			DateAndTime
		MAX-ACCESS		read-write
		STATUS			current
		DESCRIPTION		"set saving logging to everyday's time"
		::=  {  ucLogfilesave  2  }

	ucLogFSWeekWeekdayTime	OBJECT-TYPE	
		SYNTAX			Integer32  ( 1 .. 7  ) 
		MAX-ACCESS		read-write
		STATUS			current
		DESCRIPTION		"set the saving logging to week weekday time"
		::=  {  ucLogfilesave  3  }

	ucLogFSMonthMothdayTime	OBJECT-TYPE	
		SYNTAX			Integer32  ( 1 .. 31  ) 
		MAX-ACCESS		read-write
		STATUS			current
		DESCRIPTION		"set the saving logging to month monthday time"
		::=  {  ucLogfilesave  4  }

	ucLogFSFtpServerIP	OBJECT-TYPE	
		SYNTAX			IpAddress
		MAX-ACCESS		read-write
		STATUS			current
		DESCRIPTION		"the saving logging's remote ftp server's ip"
		::=  {  ucLogfilesave  5  }

	ucLogFSUserName	OBJECT-TYPE	
		SYNTAX			DisplayString  ( SIZE ( 1 .. 31  ) ) 
		MAX-ACCESS		read-write
		STATUS			current
		DESCRIPTION		"ftp login user name"
		::=  {  ucLogfilesave  6  }

	ucLogFSPassword	OBJECT-TYPE	
		SYNTAX			DisplayString  ( SIZE ( 1 .. 31  ) ) 
		MAX-ACCESS		read-write
		STATUS			current
		DESCRIPTION		"ftp login password"
		::=  {  ucLogfilesave  7  }

	ucLogFSFilename	OBJECT-TYPE	
		SYNTAX			DisplayString  ( SIZE ( 1 .. 31  ) ) 
		MAX-ACCESS		read-write
		STATUS			current
		DESCRIPTION		"file name for the ftp saving logging
default:log.dat"
		::=  {  ucLogfilesave  8  }

	ucLogFileSaveEN	OBJECT-TYPE	
		SYNTAX			INTEGER  { disable ( 0 ) , enbale ( 1 ) } 
		MAX-ACCESS		read-write
		STATUS			current
		DESCRIPTION		"alarm level"
		::=  {  ucLogfilesave  9  }

	ucLogFtpLevel	OBJECT-TYPE	
		SYNTAX			INTEGER  { disable ( 0 ) , enbale ( 1 ) } 
		MAX-ACCESS		read-write
		STATUS			current
		DESCRIPTION		"the saving logging to the ftp server's level"
		::=  {  ucLogFtp  1  }

	ucLogFtpServerIP	OBJECT-TYPE	
		SYNTAX			IpAddress
		MAX-ACCESS		read-write
		STATUS			current
		DESCRIPTION		"ftp server ip"
		::=  {  ucLogFtp  2  }

	ucLogFtpUserName	OBJECT-TYPE	
		SYNTAX			DisplayString  ( SIZE ( 1 .. 31  ) ) 
		MAX-ACCESS		read-write
		STATUS			current
		DESCRIPTION		"ftp server user name"
		::=  {  ucLogFtp  3  }

	ucLogFtpPassword	OBJECT-TYPE	
		SYNTAX			DisplayString  ( SIZE ( 1 .. 31  ) ) 
		MAX-ACCESS		read-write
		STATUS			current
		DESCRIPTION		"ftp server password"
		::=  {  ucLogFtp  4  }

	ucLogFtpFilename	OBJECT-TYPE	
		SYNTAX			DisplayString  ( SIZE ( 1 .. 31  ) ) 
		MAX-ACCESS		read-write
		STATUS			current
		DESCRIPTION		"file name of the saving logging"
		::=  {  ucLogFtp  5  }

	ucLogFtpEN	OBJECT-TYPE	
		SYNTAX			Integer32  ( -2147483648 .. 2147483647  ) 
		MAX-ACCESS		read-write
		STATUS			current
		DESCRIPTION		"logging ftp level [mng] ftp-server username password [filename]

before to set this,the logging on command should be exec,"
		::=  {  ucLogFtp  6  }

	ucSyslogServerIP	OBJECT-TYPE	
		SYNTAX			IpAddress
		MAX-ACCESS		read-write
		STATUS			current
		DESCRIPTION		"the syslog's server ip"
		::=  {  ucSyslog  1  }

	ucSyslogServerFPort	OBJECT-TYPE	
		SYNTAX			Integer32  ( 0 .. 65535  ) 
		MAX-ACCESS		read-write
		STATUS			current
		DESCRIPTION		"the syslog server's service port.
default:514"
		::=  {  ucSyslog  2  }

	ucSyslogServerLPort	OBJECT-TYPE	
		SYNTAX			Integer32  ( 0 .. 65535  ) 
		MAX-ACCESS		read-write
		STATUS			current
		DESCRIPTION		"the local port to send the syslog.
defualt:514"
		::=  {  ucSyslog  3  }

	ucOltVlanEthertypeTable	OBJECT-TYPE
		SYNTAX		SEQUENCE  OF  UcOltVlanEthertypeEntry
		MAX-ACCESS	not-accessible
		STATUS		current
		DESCRIPTION	"Description"
		::=  { ucVlan  1 }

	ucOltVlanEthertypeEntry	OBJECT-TYPE
		SYNTAX		UcOltVlanEthertypeEntry
		MAX-ACCESS	not-accessible
		STATUS		current
		DESCRIPTION	"Description"
		INDEX		{  ucOltVlanSlotIndex  }
		::=  { ucOltVlanEthertypeTable 1 }

	UcOltVlanEthertypeEntry  ::=  SEQUENCE {
		ucOltVlanSlotIndex  Integer32,
		ucOltVlanStuffing  INTEGER,
		ucOltVlanEthertype  Integer32,
		ucOltVlanUpEthertypeEn  INTEGER,
		ucOltVlanDnEthertypeEn  INTEGER
		}


	ucOltVlanSlotIndex	OBJECT-TYPE	
		SYNTAX			Integer32  ( 1 .. 16  ) 
		MAX-ACCESS		read-only
		STATUS			current
		DESCRIPTION		"Description."
		::=  {  ucOltVlanEthertypeEntry  1  }


	ucOltVlanStuffing	OBJECT-TYPE	
		SYNTAX			INTEGER  { yes ( 1 ) , no ( 2 ) } 
		MAX-ACCESS		read-write
		STATUS			current
		DESCRIPTION		"Description."
		::=  {  ucOltVlanEthertypeEntry  2  }


	ucOltVlanEthertype	OBJECT-TYPE	
		SYNTAX			Integer32  ( 1536 .. 65535  ) 
		MAX-ACCESS		read-write
		STATUS			current
		DESCRIPTION		"Description."
		::=  {  ucOltVlanEthertypeEntry  3  }


	ucOltVlanUpEthertypeEn	OBJECT-TYPE	
		SYNTAX			INTEGER  { yes ( 1 ) , no ( 2 ) } 
		MAX-ACCESS		read-write
		STATUS			current
		DESCRIPTION		"Description."
		::=  {  ucOltVlanEthertypeEntry  4  }


	ucOltVlanDnEthertypeEn	OBJECT-TYPE	
		SYNTAX			INTEGER  { yes ( 1 ) , no ( 2 ) } 
		MAX-ACCESS		read-write
		STATUS			current
		DESCRIPTION		"Description."
		::=  {  ucOltVlanEthertypeEntry  5  }

	ucOnuVlanEthertypeTable	OBJECT-TYPE
		SYNTAX		SEQUENCE  OF  UcOnuVlanEthertypeEntry
		MAX-ACCESS	not-accessible
		STATUS		current
		DESCRIPTION	"Description"
		::=  { ucVlan  2 }

	ucOnuVlanEthertypeEntry	OBJECT-TYPE
		SYNTAX		UcOnuVlanEthertypeEntry
		MAX-ACCESS	not-accessible
		STATUS		current
		DESCRIPTION	"Description"
		INDEX		{  ucOnuVlanSlotIndex, ucOnuVlanPonIndex, ucOnuVlanOnuIndex  }
		::=  { ucOnuVlanEthertypeTable 1 }

	UcOnuVlanEthertypeEntry  ::=  SEQUENCE {
		ucOnuVlanSlotIndex  Integer32,
		ucOnuVlanPonIndex  Integer32,
		ucOnuVlanOnuIndex  Integer32,
		ucOnuVlanEthertype  Integer32,
		ucOnuVlanUpEthertypeEn  INTEGER,
		ucOnuVlanDnEthertypeEn  INTEGER
		}


	ucOnuVlanSlotIndex	OBJECT-TYPE	
		SYNTAX			Integer32  ( 1 .. 16  ) 
		MAX-ACCESS		read-only
		STATUS			current
		DESCRIPTION		"Description."
		::=  {  ucOnuVlanEthertypeEntry  1  }


	ucOnuVlanPonIndex	OBJECT-TYPE	
		SYNTAX			Integer32  ( 1 .. 32  ) 
		MAX-ACCESS		read-only
		STATUS			current
		DESCRIPTION		"Description."
		::=  {  ucOnuVlanEthertypeEntry  2  }


	ucOnuVlanOnuIndex	OBJECT-TYPE	
		SYNTAX			Integer32  ( 1 .. 256  ) 
		MAX-ACCESS		read-only
		STATUS			current
		DESCRIPTION		"Description."
		::=  {  ucOnuVlanEthertypeEntry  3  }


	ucOnuVlanEthertype	OBJECT-TYPE	
		SYNTAX			Integer32  ( 1536 .. 65535  ) 
		MAX-ACCESS		read-write
		STATUS			current
		DESCRIPTION		"Description."
		::=  {  ucOnuVlanEthertypeEntry  4  }


	ucOnuVlanUpEthertypeEn	OBJECT-TYPE	
		SYNTAX			INTEGER  { yes ( 1 ) , no ( 2 ) } 
		MAX-ACCESS		read-write
		STATUS			current
		DESCRIPTION		"Description."
		::=  {  ucOnuVlanEthertypeEntry  5  }


	ucOnuVlanDnEthertypeEn	OBJECT-TYPE	
		SYNTAX			INTEGER  { yes ( 1 ) , no ( 2 ) } 
		MAX-ACCESS		read-write
		STATUS			current
		DESCRIPTION		"Description."
		::=  {  ucOnuVlanEthertypeEntry  6  }

	ucPrioVlanTable	OBJECT-TYPE
		SYNTAX		SEQUENCE  OF  UcPrioVlanEntry
		MAX-ACCESS	not-accessible
		STATUS		current
		DESCRIPTION	"Description"
		::=  { ucVlan  3 }

	ucPrioVlanEntry	OBJECT-TYPE
		SYNTAX		UcPrioVlanEntry
		MAX-ACCESS	not-accessible
		STATUS		current
		DESCRIPTION	"Description"
		INDEX		{  ucPrioSlotIndex, ucPrioPonIndex, ucPrioOnuIndex, ucPriollidIndex  }
		::=  { ucPrioVlanTable 1 }

	UcPrioVlanEntry  ::=  SEQUENCE {
		ucPrioSlotIndex  Integer32,
		ucPrioPonIndex  Integer32,
		ucPrioOnuIndex  Integer32,
		ucPriollidIndex  Integer32,
		ucPrioLLID  OCTET STRING,
		ucPrioVlan  OCTET STRING,
		ucPrioOperation  INTEGER
		}


	ucPrioSlotIndex	OBJECT-TYPE	
		SYNTAX			Integer32  ( 1 .. 16  ) 
		MAX-ACCESS		read-only
		STATUS			current
		DESCRIPTION		"Description."
		::=  {  ucPrioVlanEntry  1  }


	ucPrioPonIndex	OBJECT-TYPE	
		SYNTAX			Integer32  ( 1 .. 32  ) 
		MAX-ACCESS		read-only
		STATUS			current
		DESCRIPTION		"Description."
		::=  {  ucPrioVlanEntry  2  }


	ucPrioOnuIndex	OBJECT-TYPE	
		SYNTAX			Integer32  ( 1 .. 256  ) 
		MAX-ACCESS		read-only
		STATUS			current
		DESCRIPTION		"Description."
		::=  {  ucPrioVlanEntry  3  }


	ucPriollidIndex	OBJECT-TYPE	
		SYNTAX			Integer32  ( 1 .. 16  ) 
		MAX-ACCESS		read-only
		STATUS			current
		DESCRIPTION		"Description."
		::=  {  ucPrioVlanEntry  4  }


	ucPrioLLID	OBJECT-TYPE	
		SYNTAX			OCTET STRING  ( SIZE ( 6 .. 6  ) ) 
		MAX-ACCESS		read-only
		STATUS			current
		DESCRIPTION		"Description."
		::=  {  ucPrioVlanEntry  5  }


	ucPrioVlan	OBJECT-TYPE	
		SYNTAX			OCTET STRING  ( SIZE ( 7 .. 7  ) ) 
		MAX-ACCESS		read-write
		STATUS			current
		DESCRIPTION		"Description."
		::=  {  ucPrioVlanEntry  6  }


	ucPrioOperation	OBJECT-TYPE	
		SYNTAX			INTEGER  { none ( 1 ) , delete ( 2 ) } 
		MAX-ACCESS		read-write
		STATUS			current
		DESCRIPTION		"Description."
		::=  {  ucPrioVlanEntry  12  }

	ucVlanTagTable	OBJECT-TYPE
		SYNTAX		SEQUENCE  OF  UcVlanTagEntry
		MAX-ACCESS	not-accessible
		STATUS		current
		DESCRIPTION	"Description"
		::=  { ucVlan  4 }

	ucVlanTagEntry	OBJECT-TYPE
		SYNTAX		UcVlanTagEntry
		MAX-ACCESS	not-accessible
		STATUS		current
		DESCRIPTION	"Description"
		INDEX		{  ucVlanTagSlotIndex, ucVlanTagPonIndex, ucVlanTagOnuIndex, ucVlanTagllidIndex  }
		::=  { ucVlanTagTable 1 }

	UcVlanTagEntry  ::=  SEQUENCE {
		ucVlanTagSlotIndex  Integer32,
		ucVlanTagPonIndex  Integer32,
		ucVlanTagOnuIndex  Integer32,
		ucVlanTagllidIndex  Integer32,
		ucVlanTagLLID  OCTET STRING,
		ucVlanTagNumNTPairs  Integer32,
		ucVlanTagNTPairs  OCTET STRING
		}


	ucVlanTagSlotIndex	OBJECT-TYPE	
		SYNTAX			Integer32  ( 1 .. 16  ) 
		MAX-ACCESS		read-only
		STATUS			current
		DESCRIPTION		"Description."
		::=  {  ucVlanTagEntry  1  }


	ucVlanTagPonIndex	OBJECT-TYPE	
		SYNTAX			Integer32  ( 1 .. 32  ) 
		MAX-ACCESS		read-only
		STATUS			current
		DESCRIPTION		"Description."
		::=  {  ucVlanTagEntry  2  }


	ucVlanTagOnuIndex	OBJECT-TYPE	
		SYNTAX			Integer32  ( 1 .. 256  ) 
		MAX-ACCESS		read-only
		STATUS			current
		DESCRIPTION		"Description."
		::=  {  ucVlanTagEntry  3  }


	ucVlanTagllidIndex	OBJECT-TYPE	
		SYNTAX			Integer32  ( 1 .. 16  ) 
		MAX-ACCESS		read-only
		STATUS			current
		DESCRIPTION		"Description."
		::=  {  ucVlanTagEntry  4  }


	ucVlanTagLLID	OBJECT-TYPE	
		SYNTAX			OCTET STRING  ( SIZE ( 6 .. 6  ) ) 
		MAX-ACCESS		read-only
		STATUS			current
		DESCRIPTION		"Description."
		::=  {  ucVlanTagEntry  5  }


	ucVlanTagNumNTPairs	OBJECT-TYPE	
		SYNTAX			Integer32  ( 0 .. 7  ) 
		MAX-ACCESS		read-only
		STATUS			current
		DESCRIPTION		"Description."
		::=  {  ucVlanTagEntry  6  }


	ucVlanTagNTPairs	OBJECT-TYPE	
		SYNTAX			OCTET STRING
		MAX-ACCESS		read-write
		STATUS			current
		DESCRIPTION		"Description."
		::=  {  ucVlanTagEntry  7  }

	ucLLinkVlanTagTable	OBJECT-TYPE
		SYNTAX		SEQUENCE  OF  UcLLinkVlanTagEntry
		MAX-ACCESS	not-accessible
		STATUS		current
		DESCRIPTION	"Description"
		::=  { ucVlan  5 }

	ucLLinkVlanTagEntry	OBJECT-TYPE
		SYNTAX		UcLLinkVlanTagEntry
		MAX-ACCESS	not-accessible
		STATUS		current
		DESCRIPTION	"Description"
		INDEX		{  ucLLinkTagSlotIndex, ucLLinkTagPonIndex, ucLLinkTagOnuIndex, ucLLinkTagLLIDIndex, ucLLinkTagNVlanTag  }
		::=  { ucLLinkVlanTagTable 1 }

	UcLLinkVlanTagEntry  ::=  SEQUENCE {
		ucLLinkTagSlotIndex  Integer32,
		ucLLinkTagPonIndex  Integer32,
		ucLLinkTagOnuIndex  Integer32,
		ucLLinkTagLLIDIndex  Integer32,
		ucLLinkTagNVlanTag  Integer32,
		ucLLinkTagLLID  OCTET STRING,
		ucLLinkTagOperation  INTEGER
		}


	ucLLinkTagSlotIndex	OBJECT-TYPE	
		SYNTAX			Integer32  ( 1 .. 16  ) 
		MAX-ACCESS		read-only
		STATUS			current
		DESCRIPTION		"Description."
		::=  {  ucLLinkVlanTagEntry  1  }


	ucLLinkTagPonIndex	OBJECT-TYPE	
		SYNTAX			Integer32  ( 1 .. 32  ) 
		MAX-ACCESS		read-only
		STATUS			current
		DESCRIPTION		"Description."
		::=  {  ucLLinkVlanTagEntry  2  }


	ucLLinkTagOnuIndex	OBJECT-TYPE	
		SYNTAX			Integer32  ( 1 .. 32  ) 
		MAX-ACCESS		read-only
		STATUS			current
		DESCRIPTION		"Description."
		::=  {  ucLLinkVlanTagEntry  3  }


	ucLLinkTagLLIDIndex	OBJECT-TYPE	
		SYNTAX			Integer32  ( 1 .. 256  ) 
		MAX-ACCESS		read-only
		STATUS			current
		DESCRIPTION		"Description."
		::=  {  ucLLinkVlanTagEntry  4  }


	ucLLinkTagNVlanTag	OBJECT-TYPE	
		SYNTAX			Integer32  ( 0 .. 65535  ) 
		MAX-ACCESS		read-only
		STATUS			current
		DESCRIPTION		"Description."
		::=  {  ucLLinkVlanTagEntry  5  }


	ucLLinkTagLLID	OBJECT-TYPE	
		SYNTAX			OCTET STRING
		MAX-ACCESS		read-write
		STATUS			current
		DESCRIPTION		"Description."
		::=  {  ucLLinkVlanTagEntry  6  }


	ucLLinkTagOperation	OBJECT-TYPE	
		SYNTAX			INTEGER  { none ( 1 ) , delete ( 2 ) } 
		MAX-ACCESS		read-write
		STATUS			current
		DESCRIPTION		"Description."
		::=  {  ucLLinkVlanTagEntry  7  }

	ucLinkCrossTable	OBJECT-TYPE
		SYNTAX		SEQUENCE  OF  UcLinkCrossEntry
		MAX-ACCESS	not-accessible
		STATUS		current
		DESCRIPTION	"Description"
		::=  { ucVlan  6 }

	ucLinkCrossEntry	OBJECT-TYPE
		SYNTAX		UcLinkCrossEntry
		MAX-ACCESS	not-accessible
		STATUS		current
		DESCRIPTION	"Description"
		INDEX		{  ucLinkSlotIndex, ucLinkPonIndex, ucLinkOnuIndex, ucLinkLLIDIndex  }
		::=  { ucLinkCrossTable 1 }

	UcLinkCrossEntry  ::=  SEQUENCE {
		ucLinkSlotIndex  Integer32,
		ucLinkPonIndex  Integer32,
		ucLinkOnuIndex  Integer32,
		ucLinkLLIDIndex  Integer32,
		ucLinkLLID  DisplayString,
		ucLinkCrossLLID  DisplayString,
		ucLinkOperation  INTEGER
		}


	ucLinkSlotIndex	OBJECT-TYPE	
		SYNTAX			Integer32  ( 1 .. 16  ) 
		MAX-ACCESS		read-only
		STATUS			current
		DESCRIPTION		"Description."
		::=  {  ucLinkCrossEntry  1  }


	ucLinkPonIndex	OBJECT-TYPE	
		SYNTAX			Integer32  ( 1 .. 32  ) 
		MAX-ACCESS		read-only
		STATUS			current
		DESCRIPTION		"Description."
		::=  {  ucLinkCrossEntry  2  }


	ucLinkOnuIndex	OBJECT-TYPE	
		SYNTAX			Integer32  ( 1 .. 256  ) 
		MAX-ACCESS		read-only
		STATUS			current
		DESCRIPTION		"Description."
		::=  {  ucLinkCrossEntry  3  }


	ucLinkLLIDIndex	OBJECT-TYPE	
		SYNTAX			Integer32  ( 1 .. 256  ) 
		MAX-ACCESS		read-only
		STATUS			current
		DESCRIPTION		"Description."
		::=  {  ucLinkCrossEntry  4  }


	ucLinkLLID	OBJECT-TYPE	
		SYNTAX			DisplayString  ( SIZE ( 12 .. 12  ) ) 
		MAX-ACCESS		read-only
		STATUS			current
		DESCRIPTION		"Description."
		::=  {  ucLinkCrossEntry  5  }


	ucLinkCrossLLID	OBJECT-TYPE	
		SYNTAX			DisplayString  ( SIZE ( 12 .. 12  ) ) 
		MAX-ACCESS		read-write
		STATUS			current
		DESCRIPTION		"Description."
		::=  {  ucLinkCrossEntry  6  }


	ucLinkOperation	OBJECT-TYPE	
		SYNTAX			INTEGER  { none ( 1 ) , delete ( 2 ) } 
		MAX-ACCESS		read-write
		STATUS			current
		DESCRIPTION		"Description."
		::=  {  ucLinkCrossEntry  7  }

	ucOltPrioCMapTable	OBJECT-TYPE
		SYNTAX		SEQUENCE  OF  UcOltPrioCMapEntry
		MAX-ACCESS	not-accessible
		STATUS		current
		DESCRIPTION	"Description"
		::=  { ucVlan  7 }

	ucOltPrioCMapEntry	OBJECT-TYPE
		SYNTAX		UcOltPrioCMapEntry
		MAX-ACCESS	not-accessible
		STATUS		current
		DESCRIPTION	"Description"
		INDEX		{  ucOltPrioCMapSlotIndex  }
		::=  { ucOltPrioCMapTable 1 }

	UcOltPrioCMapEntry  ::=  SEQUENCE {
		ucOltPrioCMapSlotIndex  Integer32,
		ucOltPrioCMapPrioMA  INTEGER,
		ucOltPrioCMapPrioMB  INTEGER,
		ucOltPrioCMapABprecedence  INTEGER,
		ucOltPrioCMapDefaultCos  Integer32,
		ucOltPrioCMapPrioA0Cos  Integer32,
		ucOltPrioCMapPrioA1Cos  Integer32,
		ucOltPrioCMapPrioA2Cos  Integer32,
		ucOltPrioCMapPrioA3Cos  Integer32,
		ucOltPrioCMapPrioA4Cos  Integer32,
		ucOltPrioCMapPrioA5Cos  Integer32,
		ucOltPrioCMapPrioA6Cos  Integer32,
		ucOltPrioCMapPrioA7Cos  Integer32,
		ucOltPrioCMapPrioB0Cos  Integer32,
		ucOltPrioCMapPrioB1Cos  Integer32,
		ucOltPrioCMapPrioB2Cos  Integer32,
		ucOltPrioCMapPrioB3Cos  Integer32,
		ucOltPrioCMapPrioB4Cos  Integer32,
		ucOltPrioCMapPrioB5Cos  Integer32,
		ucOltPrioCMapPrioB6Cos  Integer32,
		ucOltPrioCMapPrioB7Cos  Integer32
		}


	ucOltPrioCMapSlotIndex	OBJECT-TYPE	
		SYNTAX			Integer32  ( 1 .. 16  ) 
		MAX-ACCESS		read-only
		STATUS			current
		DESCRIPTION		"Description."
		::=  {  ucOltPrioCMapEntry  1  }


	ucOltPrioCMapPrioMA	OBJECT-TYPE	
		SYNTAX			INTEGER  { iptos ( 1 ) , cos ( 2 ) } 
		MAX-ACCESS		read-only
		STATUS			current
		DESCRIPTION		"Description."
		::=  {  ucOltPrioCMapEntry  2  }


	ucOltPrioCMapPrioMB	OBJECT-TYPE	
		SYNTAX			INTEGER  { iptos ( 1 ) , cos ( 2 ) } 
		MAX-ACCESS		read-only
		STATUS			current
		DESCRIPTION		"Description."
		::=  {  ucOltPrioCMapEntry  3  }


	ucOltPrioCMapABprecedence	OBJECT-TYPE	
		SYNTAX			INTEGER  { modeAonly ( 1 ) , modeBonly ( 2 ) , modeAoverB ( 3 ) , modeBoverA ( 4 ) } 
		MAX-ACCESS		read-write
		STATUS			current
		DESCRIPTION		"Description."
		::=  {  ucOltPrioCMapEntry  4  }


	ucOltPrioCMapDefaultCos	OBJECT-TYPE	
		SYNTAX			Integer32  ( 0 .. 7  ) 
		MAX-ACCESS		read-write
		STATUS			current
		DESCRIPTION		"Description."
		::=  {  ucOltPrioCMapEntry  5  }


	ucOltPrioCMapPrioA0Cos	OBJECT-TYPE	
		SYNTAX			Integer32  ( 0 .. 7  ) 
		MAX-ACCESS		read-write
		STATUS			current
		DESCRIPTION		"Description."
		::=  {  ucOltPrioCMapEntry  6  }


	ucOltPrioCMapPrioA1Cos	OBJECT-TYPE	
		SYNTAX			Integer32  ( 0 .. 7  ) 
		MAX-ACCESS		read-write
		STATUS			current
		DESCRIPTION		"Description."
		::=  {  ucOltPrioCMapEntry  7  }


	ucOltPrioCMapPrioA2Cos	OBJECT-TYPE	
		SYNTAX			Integer32  ( 0 .. 7  ) 
		MAX-ACCESS		read-write
		STATUS			current
		DESCRIPTION		"Description."
		::=  {  ucOltPrioCMapEntry  8  }


	ucOltPrioCMapPrioA3Cos	OBJECT-TYPE	
		SYNTAX			Integer32  ( 0 .. 7  ) 
		MAX-ACCESS		read-write
		STATUS			current
		DESCRIPTION		"Description."
		::=  {  ucOltPrioCMapEntry  9  }


	ucOltPrioCMapPrioA4Cos	OBJECT-TYPE	
		SYNTAX			Integer32  ( 0 .. 7  ) 
		MAX-ACCESS		read-write
		STATUS			current
		DESCRIPTION		"Description."
		::=  {  ucOltPrioCMapEntry  10  }


	ucOltPrioCMapPrioA5Cos	OBJECT-TYPE	
		SYNTAX			Integer32  ( 0 .. 7  ) 
		MAX-ACCESS		read-write
		STATUS			current
		DESCRIPTION		"Description."
		::=  {  ucOltPrioCMapEntry  11  }


	ucOltPrioCMapPrioA6Cos	OBJECT-TYPE	
		SYNTAX			Integer32  ( 0 .. 7  ) 
		MAX-ACCESS		read-write
		STATUS			current
		DESCRIPTION		"Description."
		::=  {  ucOltPrioCMapEntry  12  }


	ucOltPrioCMapPrioA7Cos	OBJECT-TYPE	
		SYNTAX			Integer32  ( 0 .. 7  ) 
		MAX-ACCESS		read-write
		STATUS			current
		DESCRIPTION		"Description."
		::=  {  ucOltPrioCMapEntry  13  }


	ucOltPrioCMapPrioB0Cos	OBJECT-TYPE	
		SYNTAX			Integer32  ( 0 .. 7  ) 
		MAX-ACCESS		read-write
		STATUS			current
		DESCRIPTION		"Description."
		::=  {  ucOltPrioCMapEntry  14  }


	ucOltPrioCMapPrioB1Cos	OBJECT-TYPE	
		SYNTAX			Integer32  ( 0 .. 7  ) 
		MAX-ACCESS		read-write
		STATUS			current
		DESCRIPTION		"Description."
		::=  {  ucOltPrioCMapEntry  15  }


	ucOltPrioCMapPrioB2Cos	OBJECT-TYPE	
		SYNTAX			Integer32  ( 0 .. 7  ) 
		MAX-ACCESS		read-write
		STATUS			current
		DESCRIPTION		"Description."
		::=  {  ucOltPrioCMapEntry  16  }


	ucOltPrioCMapPrioB3Cos	OBJECT-TYPE	
		SYNTAX			Integer32  ( 0 .. 7  ) 
		MAX-ACCESS		read-write
		STATUS			current
		DESCRIPTION		"Description."
		::=  {  ucOltPrioCMapEntry  17  }


	ucOltPrioCMapPrioB4Cos	OBJECT-TYPE	
		SYNTAX			Integer32  ( 0 .. 7  ) 
		MAX-ACCESS		read-write
		STATUS			current
		DESCRIPTION		"Description."
		::=  {  ucOltPrioCMapEntry  18  }


	ucOltPrioCMapPrioB5Cos	OBJECT-TYPE	
		SYNTAX			Integer32  ( 0 .. 7  ) 
		MAX-ACCESS		read-write
		STATUS			current
		DESCRIPTION		"Description."
		::=  {  ucOltPrioCMapEntry  19  }


	ucOltPrioCMapPrioB6Cos	OBJECT-TYPE	
		SYNTAX			Integer32  ( 0 .. 7  ) 
		MAX-ACCESS		read-write
		STATUS			current
		DESCRIPTION		"Description."
		::=  {  ucOltPrioCMapEntry  20  }


	ucOltPrioCMapPrioB7Cos	OBJECT-TYPE	
		SYNTAX			Integer32  ( 0 .. 7  ) 
		MAX-ACCESS		read-write
		STATUS			current
		DESCRIPTION		"Description."
		::=  {  ucOltPrioCMapEntry  21  }

	ucOnuPVlanTable	OBJECT-TYPE
		SYNTAX		SEQUENCE  OF  UcOnuPVlanEntry
		MAX-ACCESS	not-accessible
		STATUS		current
		DESCRIPTION	"Description"
		::=  { ucVlan  8 }

	ucOnuPVlanEntry	OBJECT-TYPE
		SYNTAX		UcOnuPVlanEntry
		MAX-ACCESS	not-accessible
		STATUS		current
		DESCRIPTION	"Description"
		INDEX		{  ucOnuPVlanSlotIndex, ucOnuPVlanPonIndex, ucOnuPVlanOnuIndex, ucOnuPVlanPortIndex  }
		::=  { ucOnuPVlanTable 1 }

	UcOnuPVlanEntry  ::=  SEQUENCE {
		ucOnuPVlanSlotIndex  Integer32,
		ucOnuPVlanPonIndex  Integer32,
		ucOnuPVlanOnuIndex  Integer32,
		ucOnuPVlanPortIndex  Integer32,
		ucOnuPVlanNumVlans  Integer32,
		ucOnuPVlanmembership  OCTET STRING
		}


	ucOnuPVlanSlotIndex	OBJECT-TYPE	
		SYNTAX			Integer32  ( 1 .. 16  ) 
		MAX-ACCESS		read-only
		STATUS			current
		DESCRIPTION		"Description."
		::=  {  ucOnuPVlanEntry  1  }


	ucOnuPVlanPonIndex	OBJECT-TYPE	
		SYNTAX			Integer32  ( 1 .. 32  ) 
		MAX-ACCESS		read-only
		STATUS			current
		DESCRIPTION		"Description."
		::=  {  ucOnuPVlanEntry  2  }


	ucOnuPVlanOnuIndex	OBJECT-TYPE	
		SYNTAX			Integer32  ( 1 .. 256  ) 
		MAX-ACCESS		read-only
		STATUS			current
		DESCRIPTION		"Description."
		::=  {  ucOnuPVlanEntry  3  }


	ucOnuPVlanPortIndex	OBJECT-TYPE	
		SYNTAX			Integer32  ( 1 .. 24  ) 
		MAX-ACCESS		read-only
		STATUS			current
		DESCRIPTION		"Description."
		::=  {  ucOnuPVlanEntry  4  }


	ucOnuPVlanNumVlans	OBJECT-TYPE	
		SYNTAX			Integer32  ( 0 .. 16  ) 
		MAX-ACCESS		read-only
		STATUS			current
		DESCRIPTION		"table of VLAN Domain membership."
		::=  {  ucOnuPVlanEntry  11  }


	ucOnuPVlanmembership	OBJECT-TYPE	
		SYNTAX			OCTET STRING  ( SIZE ( 0 .. 224  ) ) 
		MAX-ACCESS		read-write
		STATUS			current
		DESCRIPTION		"Ingress VLAN tag
                          Translated VLAN tag
                          Ingress Tag Modification
                            0: Pass unmodified
                            1: Add VLAN Tag (only if frame is untagged)
                            2: Remove VLAN Tag (outermost tag, if any)
                            3: Replace (outermost) VLAN Tag
                            4: Stack VLAN Tag (add a tag in addition to existing tags)
                          Egress Tag Modification
                            (see Ingress Tagging Behavior, above, for allowed values)
                          Flags (reserved)"
		::=  {  ucOnuPVlanEntry  12  }
		
	--- ---------- Start ucOnuPVlan4d13Table ---------------	
	ucOnuPVlan4d13Table	OBJECT-TYPE
		SYNTAX		SEQUENCE  OF  UcOnuPVlan4d13Entry
		MAX-ACCESS	not-accessible
		STATUS		current
		DESCRIPTION	"Description"
		::=  { ucVlan  9 }

	ucOnuPVlan4d13Entry	OBJECT-TYPE
		SYNTAX		UcOnuPVlan4d13Entry
		MAX-ACCESS	not-accessible
		STATUS		current
		DESCRIPTION	"Description"
		INDEX		{  ucOnuPVlanSlot4d13Index, 
		           ucOnuPVlan4d13PonIndex, 
		           ucOnuPVlan4d13OnuIndex, 
		           ucOnuPVlan4d13PortIndex  }
		::=  { ucOnuPVlan4d13Table 1 }

	UcOnuPVlan4d13Entry  ::=  SEQUENCE {
		ucOnuPVlan4d13SlotIndex  Integer32,
		ucOnuPVlan4d13PonIndex   Integer32,
		ucOnuPVlan4d13OnuIndex   Integer32,
		ucOnuPVlan4d13PortIndex  Integer32,
		ucOnuPVlan4d13VID        Integer32
		}


	ucOnuPVlan4d13SlotIndex	OBJECT-TYPE	
		SYNTAX			Integer32  ( 1 .. 16  ) 
		MAX-ACCESS		read-only
		STATUS			current
		DESCRIPTION		"Description."
		::=  {  ucOnuPVlan4d13Entry  1  }


	ucOnuPVlan4d13PonIndex	OBJECT-TYPE	
		SYNTAX			Integer32  ( 1 .. 48  ) 
		MAX-ACCESS		read-only
		STATUS			current
		DESCRIPTION		"Description."
		::=  {  ucOnuPVlan4d13Entry  2  }


	ucOnuPVlan4d13OnuIndex	OBJECT-TYPE	
		SYNTAX			Integer32  ( 1 .. 256  ) 
		MAX-ACCESS		read-only
		STATUS			current
		DESCRIPTION		"Description."
		::=  {  ucOnuPVlan4d13Entry  3  }


	ucOnuPVlan4d13PortIndex	OBJECT-TYPE	
		SYNTAX			Integer32  ( 1 .. 24  ) 
		MAX-ACCESS		read-only
		STATUS			current
		DESCRIPTION		"Description."
		::=  {  ucOnuPVlan4d13Entry  4  }


	ucOnuPVlan4d13VID	OBJECT-TYPE	
		SYNTAX			Integer32  ( 0 .. 4095  ) 
		MAX-ACCESS	read-write
		STATUS			current
		DESCRIPTION		"VLAN of the each port"
		::=  {  ucOnuPVlan4d13Entry  5  }
			
  --- ---------- End ucOnuPVlan4d13Table ---------------
   
   
	ucOnuBridgeTable	OBJECT-TYPE
		SYNTAX		SEQUENCE  OF  UcOnuBridgeEntry
		MAX-ACCESS	not-accessible
		STATUS		current
		DESCRIPTION	"Description"
		::=  { ucFrameFilter  1 }

	ucOnuBridgeEntry	OBJECT-TYPE
		SYNTAX		UcOnuBridgeEntry
		MAX-ACCESS	not-accessible
		STATUS		current
		DESCRIPTION	"Description"
		INDEX		{  ucOnuBridgeSlotIndex, ucOnuBridgePonIndex, ucOnuBridgeOnuIndex, ucOnuBridgePortIndex  }
		::=  { ucOnuBridgeTable 1 }

	UcOnuBridgeEntry  ::=  SEQUENCE {
		ucOnuBridgeSlotIndex  Integer32,
		ucOnuBridgePonIndex  Integer32,
		ucOnuBridgeOnuIndex  Integer32,
		ucOnuBridgePortIndex  Integer32,
		ucOnuBridgeAutoLearnLMT  Integer32,
		ucOnuBridgeLearnAgeLMT  Integer32,
		ucOnuBridgeForwardMode  INTEGER,
		ucOnuBridgeMinLearnLMT  Integer32
		}


	ucOnuBridgeSlotIndex	OBJECT-TYPE	
		SYNTAX			Integer32  ( 1 .. 16  ) 
		MAX-ACCESS		read-only
		STATUS			current
		DESCRIPTION		"Description."
		::=  {  ucOnuBridgeEntry  1  }


	ucOnuBridgePonIndex	OBJECT-TYPE	
		SYNTAX			Integer32  ( 1 .. 32  ) 
		MAX-ACCESS		read-only
		STATUS			current
		DESCRIPTION		"Description."
		::=  {  ucOnuBridgeEntry  2  }


	ucOnuBridgeOnuIndex	OBJECT-TYPE	
		SYNTAX			Integer32  ( 1 .. 256  ) 
		MAX-ACCESS		read-only
		STATUS			current
		DESCRIPTION		"Description."
		::=  {  ucOnuBridgeEntry  3  }


	ucOnuBridgePortIndex	OBJECT-TYPE	
		SYNTAX			Integer32  ( 1 .. 24  ) 
		MAX-ACCESS		read-only
		STATUS			current
		DESCRIPTION		"Description."
		::=  {  ucOnuBridgeEntry  4  }


	ucOnuBridgeAutoLearnLMT	OBJECT-TYPE	
		SYNTAX			Integer32  ( 0 .. 64  ) 
		MAX-ACCESS		read-write
		STATUS			current
		DESCRIPTION		"Description."
		::=  {  ucOnuBridgeEntry  5  }


	ucOnuBridgeLearnAgeLMT	OBJECT-TYPE	
		SYNTAX			Integer32  ( 0 .. 32768  ) 
		MAX-ACCESS		read-write
		STATUS			current
		DESCRIPTION		"Description."
		::=  {  ucOnuBridgeEntry  6  }


	ucOnuBridgeForwardMode	OBJECT-TYPE	
		SYNTAX			INTEGER  { forward ( 1 ) , dropUntilLearn ( 2 ) } 
		MAX-ACCESS		read-write
		STATUS			current
		DESCRIPTION		"Description."
		::=  {  ucOnuBridgeEntry  7  }


	ucOnuBridgeMinLearnLMT	OBJECT-TYPE	
		SYNTAX			Integer32  ( 0 .. 64  ) 
		MAX-ACCESS		read-write
		STATUS			current
		DESCRIPTION		"Description."
		::=  {  ucOnuBridgeEntry  8  }

	ucOnuBridgeConfTable	OBJECT-TYPE
		SYNTAX		SEQUENCE  OF  UcOnuBridgeConfEntry
		MAX-ACCESS	not-accessible
		STATUS		current
		DESCRIPTION	"Description"
		::=  { ucFrameFilter  2 }

	ucOnuBridgeConfEntry	OBJECT-TYPE
		SYNTAX		UcOnuBridgeConfEntry
		MAX-ACCESS	not-accessible
		STATUS		current
		DESCRIPTION	"Description"
		INDEX		{  ucOnuBConfSlotIndex, ucOnuBConfPonIndex, ucOnuBConfOnuIndex  }
		::=  { ucOnuBridgeConfTable 1 }

	UcOnuBridgeConfEntry  ::=  SEQUENCE {
		ucOnuBConfSlotIndex  Integer32,
		ucOnuBConfPonIndex  Integer32,
		ucOnuBConfOnuIndex  Integer32,
		ucOnuBConfAggregateOnuLearnLMT  Integer32,
		ucOnuBConfFloodUnknownDAOpt  INTEGER,
		ucOnuBConfLocalSWOpt  INTEGER,
		ucOnuBConfDnBurstOpt  INTEGER
		}


	ucOnuBConfSlotIndex	OBJECT-TYPE	
		SYNTAX			Integer32  ( 1 .. 16  ) 
		MAX-ACCESS		read-only
		STATUS			current
		DESCRIPTION		"Description."
		::=  {  ucOnuBridgeConfEntry  1  }


	ucOnuBConfPonIndex	OBJECT-TYPE	
		SYNTAX			Integer32  ( 1 .. 32  ) 
		MAX-ACCESS		read-only
		STATUS			current
		DESCRIPTION		"Description."
		::=  {  ucOnuBridgeConfEntry  2  }


	ucOnuBConfOnuIndex	OBJECT-TYPE	
		SYNTAX			Integer32  ( 1 .. 256  ) 
		MAX-ACCESS		read-only
		STATUS			current
		DESCRIPTION		"Description."
		::=  {  ucOnuBridgeConfEntry  3  }


	ucOnuBConfAggregateOnuLearnLMT	OBJECT-TYPE	
		SYNTAX			Integer32  ( 0 .. 64  ) 
		MAX-ACCESS		read-write
		STATUS			current
		DESCRIPTION		"Description."
		::=  {  ucOnuBridgeConfEntry  4  }


	ucOnuBConfFloodUnknownDAOpt	OBJECT-TYPE	
		SYNTAX			INTEGER  { drop ( 1 ) , flood ( 2 ) } 
		MAX-ACCESS		read-write
		STATUS			current
		DESCRIPTION		"Description."
		::=  {  ucOnuBridgeConfEntry  5  }


	ucOnuBConfLocalSWOpt	OBJECT-TYPE	
		SYNTAX			INTEGER  { disableSw ( 1 ) , enableSw ( 2 ) } 
		MAX-ACCESS		read-write
		STATUS			current
		DESCRIPTION		"Description."
		::=  {  ucOnuBridgeConfEntry  6  }


	ucOnuBConfDnBurstOpt	OBJECT-TYPE	
		SYNTAX			INTEGER  { disable ( 1 ) , enable ( 2 ) } 
		MAX-ACCESS		read-write
		STATUS			current
		DESCRIPTION		"Description."
		::=  {  ucOnuBridgeConfEntry  7  }

	ucOnuDynamicBridgeTable	OBJECT-TYPE
		SYNTAX		SEQUENCE  OF  UcOnuDynamicBridgeEntry
		MAX-ACCESS	not-accessible
		STATUS		current
		DESCRIPTION	"Description"
		::=  { ucFrameFilter  3 }

	ucOnuDynamicBridgeEntry	OBJECT-TYPE
		SYNTAX		UcOnuDynamicBridgeEntry
		MAX-ACCESS	not-accessible
		STATUS		current
		DESCRIPTION	"Description"
		INDEX		{  ucOnuDynamicBSlotIndex, ucOnuDynamicBPonIndex, ucOnuDynamicBOnuIndex, ucOnuDynamicBPortIndex  }
		::=  { ucOnuDynamicBridgeTable 1 }

	UcOnuDynamicBridgeEntry  ::=  SEQUENCE {
		ucOnuDynamicBSlotIndex  Integer32,
		ucOnuDynamicBPonIndex  Integer32,
		ucOnuDynamicBOnuIndex  Integer32,
		ucOnuDynamicBPortIndex  Integer32,
		ucOnuDynamicBMACEntrys  Integer32,
		ucOnuDynamicBMAC  OCTET STRING,
		ucOnuDynamicBOperation  INTEGER
		}


	ucOnuDynamicBSlotIndex	OBJECT-TYPE	
		SYNTAX			Integer32  ( 1 .. 16  ) 
		MAX-ACCESS		read-only
		STATUS			current
		DESCRIPTION		"Description."
		::=  {  ucOnuDynamicBridgeEntry  1  }


	ucOnuDynamicBPonIndex	OBJECT-TYPE	
		SYNTAX			Integer32  ( 1 .. 32  ) 
		MAX-ACCESS		read-only
		STATUS			current
		DESCRIPTION		"Description."
		::=  {  ucOnuDynamicBridgeEntry  2  }


	ucOnuDynamicBOnuIndex	OBJECT-TYPE	
		SYNTAX			Integer32  ( 1 .. 256  ) 
		MAX-ACCESS		read-only
		STATUS			current
		DESCRIPTION		"Description."
		::=  {  ucOnuDynamicBridgeEntry  3  }


	ucOnuDynamicBPortIndex	OBJECT-TYPE	
		SYNTAX			Integer32  ( 1 .. 24  ) 
		MAX-ACCESS		read-only
		STATUS			current
		DESCRIPTION		"Description."
		::=  {  ucOnuDynamicBridgeEntry  4  }


	ucOnuDynamicBMACEntrys	OBJECT-TYPE	
		SYNTAX			Integer32  ( 1 .. 65536  ) 
		MAX-ACCESS		read-only
		STATUS			current
		DESCRIPTION		"Description."
		::=  {  ucOnuDynamicBridgeEntry  5  }


	ucOnuDynamicBMAC	OBJECT-TYPE	
		SYNTAX			OCTET STRING
		MAX-ACCESS		read-only
		STATUS			current
		DESCRIPTION		"Description."
		::=  {  ucOnuDynamicBridgeEntry  6  }


	ucOnuDynamicBOperation	OBJECT-TYPE	
		SYNTAX			INTEGER  { none ( 1 ) , clearAllOnPort ( 2 ) } 
		MAX-ACCESS		read-write
		STATUS			current
		DESCRIPTION		"Description."
		::=  {  ucOnuDynamicBridgeEntry  7  }

	ucOltBridgeModeTable	OBJECT-TYPE
		SYNTAX		SEQUENCE  OF  UcOltBridgeModeEntry
		MAX-ACCESS	not-accessible
		STATUS		current
		DESCRIPTION	"Description"
		::=  { ucFrameFilter  4 }

	ucOltBridgeModeEntry	OBJECT-TYPE
		SYNTAX		UcOltBridgeModeEntry
		MAX-ACCESS	not-accessible
		STATUS		current
		DESCRIPTION	"Description"
		INDEX		{  ucOltBridgeMSlotIndex, ucOltBridgeMPonIndex, ucOltBridgeMOnuIndex, ucOltBridgeMLLIDIndex  }
		::=  { ucOltBridgeModeTable 1 }

	UcOltBridgeModeEntry  ::=  SEQUENCE {
		ucOltBridgeMSlotIndex  Integer32,
		ucOltBridgeMPonIndex  Integer32,
		ucOltBridgeMOnuIndex  Integer32,
		ucOltBridgeMLLIDIndex  Integer32,
		ucOltBridgeMLLID  DisplayString,
		ucOltBridgeMMode  INTEGER,
		ucOltBridgeMMacEntryLMT  Integer32
		}


	ucOltBridgeMSlotIndex	OBJECT-TYPE	
		SYNTAX			Integer32  ( 1 .. 16  ) 
		MAX-ACCESS		read-only
		STATUS			current
		DESCRIPTION		"Description."
		::=  {  ucOltBridgeModeEntry  1  }


	ucOltBridgeMPonIndex	OBJECT-TYPE	
		SYNTAX			Integer32  ( 1 .. 32  ) 
		MAX-ACCESS		read-only
		STATUS			current
		DESCRIPTION		"Description."
		::=  {  ucOltBridgeModeEntry  2  }


	ucOltBridgeMOnuIndex	OBJECT-TYPE	
		SYNTAX			Integer32  ( 1 .. 256  ) 
		MAX-ACCESS		read-only
		STATUS			current
		DESCRIPTION		"Description."
		::=  {  ucOltBridgeModeEntry  3  }


	ucOltBridgeMLLIDIndex	OBJECT-TYPE	
		SYNTAX			Integer32  ( 1 .. 256  ) 
		MAX-ACCESS		read-only
		STATUS			current
		DESCRIPTION		"Description."
		::=  {  ucOltBridgeModeEntry  4  }


	ucOltBridgeMLLID	OBJECT-TYPE	
		SYNTAX			DisplayString  ( SIZE ( 12 .. 12  ) ) 
		MAX-ACCESS		read-only
		STATUS			current
		DESCRIPTION		"Description."
		::=  {  ucOltBridgeModeEntry  5  }


	ucOltBridgeMMode	OBJECT-TYPE	
		SYNTAX			INTEGER  { bridging ( 0 ) , singleVlan ( 1 ) , doubleVlan ( 2 ) , sharedVlan ( 3 ) , transparentVlan ( 4 ) , translatedVlan ( 5 ) , crossConnect ( 6 ) , priVlan ( 7 ) , tosBasedSingleVlan ( 8 ) , tosBasedDoubleVlan ( 9 ) , tosBasedSharedVlan ( 10 ) , prioritySharedVlan ( 11 ) , prioritizedBridge ( 12 ) , transparentPrioritySharedVlan ( 13 ) , transparentSharedVlanWithBcast ( 14 ) , doubleTaggedSharedVlan ( 15 ) } 
		MAX-ACCESS		read-write
		STATUS			current
		DESCRIPTION		"Description."
		::=  {  ucOltBridgeModeEntry  6  }


	ucOltBridgeMMacEntryLMT	OBJECT-TYPE	
		SYNTAX			Integer32  ( 0 .. 4095  ) 
		MAX-ACCESS		read-write
		STATUS			current
		DESCRIPTION		"Description."
		::=  {  ucOltBridgeModeEntry  7  }

	ucOltDynmicBridgeEntryTable	OBJECT-TYPE
		SYNTAX		SEQUENCE  OF  UcOltDynmicBridgeEntryEntry
		MAX-ACCESS	not-accessible
		STATUS		current
		DESCRIPTION	"Description"
		::=  { ucFrameFilter  5 }

	ucOltDynmicBridgeEntryEntry	OBJECT-TYPE
		SYNTAX		UcOltDynmicBridgeEntryEntry
		MAX-ACCESS	not-accessible
		STATUS		current
		DESCRIPTION	"Description"
		INDEX		{  ucOltDynmicBridgeESlotIndex, ucOltDynmicBridgeEPonIndex, ucOltDynmicBridgeEOnuIndex, ucOltDynmicBridgeELLIDIndex  }
		::=  { ucOltDynmicBridgeEntryTable 1 }

	UcOltDynmicBridgeEntryEntry  ::=  SEQUENCE {
		ucOltDynmicBridgeESlotIndex  Integer32,
		ucOltDynmicBridgeEPonIndex  Integer32,
		ucOltDynmicBridgeEOnuIndex  Integer32,
		ucOltDynmicBridgeELLIDIndex  Integer32,
		ucOltDynmicBridgeELLID  OCTET STRING,
		ucOltDynmicBridgeEntrys  Integer32,
		ucOltDynmicBridgeEMAC  OCTET STRING,
		ucOltDynmicBridgeEOperation  INTEGER
		}


	ucOltDynmicBridgeESlotIndex	OBJECT-TYPE	
		SYNTAX			Integer32  ( 1 .. 16  ) 
		MAX-ACCESS		read-only
		STATUS			current
		DESCRIPTION		"Description."
		::=  {  ucOltDynmicBridgeEntryEntry  1  }


	ucOltDynmicBridgeEPonIndex	OBJECT-TYPE	
		SYNTAX			Integer32  ( 1 .. 32  ) 
		MAX-ACCESS		read-only
		STATUS			current
		DESCRIPTION		"Description."
		::=  {  ucOltDynmicBridgeEntryEntry  2  }


	ucOltDynmicBridgeEOnuIndex	OBJECT-TYPE	
		SYNTAX			Integer32  ( 1 .. 256  ) 
		MAX-ACCESS		read-only
		STATUS			current
		DESCRIPTION		"Description."
		::=  {  ucOltDynmicBridgeEntryEntry  3  }


	ucOltDynmicBridgeELLIDIndex	OBJECT-TYPE	
		SYNTAX			Integer32  ( 1 .. 256  ) 
		MAX-ACCESS		read-only
		STATUS			current
		DESCRIPTION		"Description."
		::=  {  ucOltDynmicBridgeEntryEntry  4  }


	ucOltDynmicBridgeELLID	OBJECT-TYPE	
		SYNTAX			OCTET STRING  ( SIZE ( 6 .. 6  ) ) 
		MAX-ACCESS		read-only
		STATUS			current
		DESCRIPTION		"Description."
		::=  {  ucOltDynmicBridgeEntryEntry  5  }


	ucOltDynmicBridgeEntrys	OBJECT-TYPE	
		SYNTAX			Integer32  ( 0 .. 4096  ) 
		MAX-ACCESS		read-only
		STATUS			current
		DESCRIPTION		"Description."
		::=  {  ucOltDynmicBridgeEntryEntry  6  }


	ucOltDynmicBridgeEMAC	OBJECT-TYPE	
		SYNTAX			OCTET STRING
		MAX-ACCESS		read-only
		STATUS			current
		DESCRIPTION		"Description."
		::=  {  ucOltDynmicBridgeEntryEntry  7  }


	ucOltDynmicBridgeEOperation	OBJECT-TYPE	
		SYNTAX			INTEGER  { none ( 1 ) , clearAllonlink ( 2 ) , clearAllonOlt ( 3 ) } 
		MAX-ACCESS		read-write
		STATUS			current
		DESCRIPTION		"Description."
		::=  {  ucOltDynmicBridgeEntryEntry  8  }

	ucOltBridgeConfTable	OBJECT-TYPE
		SYNTAX		SEQUENCE  OF  UcOltBridgeConfEntry
		MAX-ACCESS	not-accessible
		STATUS		current
		DESCRIPTION	"Description"
		::=  { ucFrameFilter  6 }

	ucOltBridgeConfEntry	OBJECT-TYPE
		SYNTAX		UcOltBridgeConfEntry
		MAX-ACCESS	not-accessible
		STATUS		current
		DESCRIPTION	"Description"
		INDEX		{  ucOltBridgeCSlotIndex  }
		::=  { ucOltBridgeConfTable 1 }

	UcOltBridgeConfEntry  ::=  SEQUENCE {
		ucOltBridgeCSlotIndex  Integer32,
		ucOltBridgeCLearnEntryAgeLMT  Integer32,
		ucOltBridgeCDnFrameResetAge  INTEGER,
		ucOltBridgeCBridgeVlans  Integer32,
		ucOltBridgeCSimpleBridge  INTEGER,
		ucOltBridgeCMACOverwrite  INTEGER,
		ucOltBridgeCDiscardUMAC  INTEGER,
		ucOltBridgeCAllowTagged  INTEGER,
		ucOltBridgeConfigCtrl  DisplayString
		}


	ucOltBridgeCSlotIndex	OBJECT-TYPE	
		SYNTAX			Integer32  ( 1 .. 16  ) 
		MAX-ACCESS		read-only
		STATUS			current
		DESCRIPTION		"Description."
		::=  {  ucOltBridgeConfEntry  1  }


	ucOltBridgeCLearnEntryAgeLMT	OBJECT-TYPE	
		SYNTAX			Integer32  ( 0 .. 32768  ) 
		MAX-ACCESS		read-write
		STATUS			current
		DESCRIPTION		"Description."
		::=  {  ucOltBridgeConfEntry  2  }


	ucOltBridgeCDnFrameResetAge	OBJECT-TYPE	
		SYNTAX			INTEGER  { yes ( 1 ) , no ( 2 ) } 
		MAX-ACCESS		read-write
		STATUS			current
		DESCRIPTION		"Description."
		::=  {  ucOltBridgeConfEntry  3  }


	ucOltBridgeCBridgeVlans	OBJECT-TYPE	
		SYNTAX			Integer32  ( 0 .. 30  ) 
		MAX-ACCESS		read-write
		STATUS			current
		DESCRIPTION		"Description."
		::=  {  ucOltBridgeConfEntry  4  }


	ucOltBridgeCSimpleBridge	OBJECT-TYPE	
		SYNTAX			INTEGER  { yes ( 1 ) , no ( 2 ) } 
		MAX-ACCESS		read-write
		STATUS			current
		DESCRIPTION		"Description."
		::=  {  ucOltBridgeConfEntry  5  }


	ucOltBridgeCMACOverwrite	OBJECT-TYPE	
		SYNTAX			INTEGER  { yes ( 1 ) , no ( 2 ) } 
		MAX-ACCESS		read-write
		STATUS			current
		DESCRIPTION		"Description."
		::=  {  ucOltBridgeConfEntry  6  }


	ucOltBridgeCDiscardUMAC	OBJECT-TYPE	
		SYNTAX			INTEGER  { yes ( 1 ) , no ( 2 ) } 
		MAX-ACCESS		read-write
		STATUS			current
		DESCRIPTION		"Description."
		::=  {  ucOltBridgeConfEntry  7  }


	ucOltBridgeCAllowTagged	OBJECT-TYPE	
		SYNTAX			INTEGER  { yes ( 1 ) , no ( 2 ) } 
		MAX-ACCESS		read-write
		STATUS			current
		DESCRIPTION		"Description."
		::=  {  ucOltBridgeConfEntry  8  }


	ucOltBridgeConfigCtrl	OBJECT-TYPE	
		SYNTAX			DisplayString
		MAX-ACCESS		read-write
		STATUS			current
		DESCRIPTION		"Size Description
4 Learned entry age limit (Note TK37xx hardware limits ages to values of
   the form 2 ^ N * 8.75 ms, +/- 12.5%.
   Provisioned values will be rounded up to the
   next higher increment. An age limit of 0
   disables aging.)----Units(8.75 ms)--Default(0)--Min(0)--Max(32768)
1 Downstream Frames Reset Age ( If enabled,
   frames received by the OLT LNP port reset the
   learned entry age value for dynamic entries
   based on DA of incoming frame. In this mode
   upstream frames will also reset the age value
   based on SA as normal.(Yes = 1, No = 0).)----Default(0 (No))
1 Number of Bridged VLANs (deducted from
   the total number of LLIDs that may be
   registered)----Units(bridges)--Default(24)--Min(0)--Max(30)
1 Allow Simple Bridging (1 = Yes, 0 = No).(
   Affects the number of Bridged VLANs
   parameter. (Currently must set to 1))----Default(1 (Yes))
1 MAC Learning overwrite----Default(0)--Max(1)
1 Discard Unknown MAC----Default(0)--Max(1)
1 Bridge Configuration Parameter 1(
   Bit0: Allow Tagged Frames on Simple Bridge
   Bit1..7: Reserved)----Default(0)--Max(1)
1 Reserved ----Default(0)
1 Reserved ----Default(0)
1 Reserved ----Default(0)
1 Reserved ----Default(0)
1 Reserved ----Default(0)
1 Reserved ----Default(0)"
		::=  {  ucOltBridgeConfEntry  9  }

	ucOnuPortIngressTable	OBJECT-TYPE
		SYNTAX		SEQUENCE  OF  UcOnuPortIngressEntry
		MAX-ACCESS	not-accessible
		STATUS		current
		DESCRIPTION	"Description"
		::=  { ucFrameFilter  8 }

	ucOnuPortIngressEntry	OBJECT-TYPE
		SYNTAX		UcOnuPortIngressEntry
		MAX-ACCESS	not-accessible
		STATUS		current
		DESCRIPTION	"Description"
		INDEX		{  ucOnuPortInSlotIndex, ucOnuPortInPonIndex, ucOnuPortInOnuIndex, ucOnuPortInPortIndex  }
		::=  { ucOnuPortIngressTable 1 }

	UcOnuPortIngressEntry  ::=  SEQUENCE {
		ucOnuPortInSlotIndex  Integer32,
		ucOnuPortInPonIndex  Integer32,
		ucOnuPortInOnuIndex  Integer32,
		ucOnuPortInPortIndex  Integer32,
		ucIngressRateLevel  OCTET STRING
		}


	ucOnuPortInSlotIndex	OBJECT-TYPE	
		SYNTAX			Integer32  ( 1 .. 16  ) 
		MAX-ACCESS		read-only
		STATUS			current
		DESCRIPTION		"Description."
		::=  {  ucOnuPortIngressEntry  1  }


	ucOnuPortInPonIndex	OBJECT-TYPE	
		SYNTAX			Integer32  ( 1 .. 32  ) 
		MAX-ACCESS		read-only
		STATUS			current
		DESCRIPTION		"Description."
		::=  {  ucOnuPortIngressEntry  2  }


	ucOnuPortInOnuIndex	OBJECT-TYPE	
		SYNTAX			Integer32  ( 1 .. 256  ) 
		MAX-ACCESS		read-only
		STATUS			current
		DESCRIPTION		"Description."
		::=  {  ucOnuPortIngressEntry  3  }


	ucOnuPortInPortIndex	OBJECT-TYPE	
		SYNTAX			Integer32  ( 1 .. 24  ) 
		MAX-ACCESS		read-only
		STATUS			current
		DESCRIPTION		"Description."
		::=  {  ucOnuPortIngressEntry  4  }


	ucIngressRateLevel	OBJECT-TYPE	
		SYNTAX			OCTET STRING  ( SIZE ( 10 .. 50  ) ) 
		MAX-ACCESS		read-write
		STATUS			current
		DESCRIPTION		"Description."
		::=  {  ucOnuPortIngressEntry  5  }

	ucOnuRulesTable	OBJECT-TYPE
		SYNTAX		SEQUENCE  OF  UcOnuRulesEntry
		MAX-ACCESS	not-accessible
		STATUS		current
		DESCRIPTION	"Description"
		::=  { ucFrameFilter  9 }

	ucOnuRulesEntry	OBJECT-TYPE
		SYNTAX		UcOnuRulesEntry
		MAX-ACCESS	not-accessible
		STATUS		current
		DESCRIPTION	"Description"
		INDEX		{  ucOnuRulesSlotIndex, ucOnuRulesPonIndex, ucOnuRulesOnuIndex, ucOnuRulesChipPortIndex  }
		::=  { ucOnuRulesTable 1 }

	UcOnuRulesEntry  ::=  SEQUENCE {
		ucOnuRulesSlotIndex  Integer32,
		ucOnuRulesPonIndex  Integer32,
		ucOnuRulesOnuIndex  Integer32,
		ucOnuRulesChipPortIndex  Integer32,
		ucOnuRulesCount  Integer32,
		ucOnuRulesRules  DisplayString,
		ucOnuRulesDeleteRules  DisplayString,
		ucOnuLueFieldSelectors  DisplayString
		}


	ucOnuRulesSlotIndex	OBJECT-TYPE	
		SYNTAX			Integer32  ( 1 .. 16  ) 
		MAX-ACCESS		read-only
		STATUS			current
		DESCRIPTION		"Description."
		::=  {  ucOnuRulesEntry  1  }


	ucOnuRulesPonIndex	OBJECT-TYPE	
		SYNTAX			Integer32  ( 1 .. 32  ) 
		MAX-ACCESS		read-only
		STATUS			current
		DESCRIPTION		"Description."
		::=  {  ucOnuRulesEntry  2  }


	ucOnuRulesOnuIndex	OBJECT-TYPE	
		SYNTAX			Integer32  ( 1 .. 256  ) 
		MAX-ACCESS		read-only
		STATUS			current
		DESCRIPTION		"Description."
		::=  {  ucOnuRulesEntry  3  }


	ucOnuRulesChipPortIndex	OBJECT-TYPE	
		SYNTAX			Integer32  ( 1 .. 3  ) 
		MAX-ACCESS		read-only
		STATUS			current
		DESCRIPTION		"Description."
		::=  {  ucOnuRulesEntry  4  }


	ucOnuRulesCount	OBJECT-TYPE	
		SYNTAX			Integer32  ( 1 .. 256  ) 
		MAX-ACCESS		read-only
		STATUS			current
		DESCRIPTION		"Description."
		::=  {  ucOnuRulesEntry  5  }


	ucOnuRulesRules	OBJECT-TYPE	
		SYNTAX			DisplayString  ( SIZE ( 0 .. 4096  ) ) 
		MAX-ACCESS		read-write
		STATUS			current
		DESCRIPTION		"
				                "
		::=  {  ucOnuRulesEntry  6  }


	ucOnuRulesDeleteRules	OBJECT-TYPE	
		SYNTAX			DisplayString  ( SIZE ( 0 .. 4096  ) ) 
		MAX-ACCESS		read-write
		STATUS			current
		DESCRIPTION		"Description."
		::=  {  ucOnuRulesEntry  7  }


	ucOnuLueFieldSelectors	OBJECT-TYPE	
		SYNTAX			DisplayString  ( SIZE ( 0 .. 255  ) ) 
		MAX-ACCESS		read-write
		STATUS			current
		DESCRIPTION		"Size   Description
1 Number of fields to follow----Min(8)--Max(255)
     Field 1 description
1   Reference Count ----Units(Number of clauses)--Min(0)--Max(255)
1   Layer select----Min(0)--Max(7)
1   Dword offset----Min(0)--Max(8)
1   Least significant bit----Min(0)--Max(31)
1   Bit width----Min(1)--Max(32)
     Field 2 description...
     ...
     Field N description...


In the Get response, the Number of Fields is the maximum number of fields the ONU can support. The current
programming of each field is described. The Reference Count indicates the number of clauses in rules that are
currently using this field. If the field is currently unused, the reference count will be zero, and the layer select,
dword offset, least significant bit, and bit width will contain the maximum possible values for that field on that
ONU. Fields with a non-zero reference count can not be reprogrammed with the Set message. All rules using a
given field must be deleted before the meaning of that field is changed. Note that hardware and firmware system
rules will also use fields in the LUE. These rules cannot be deleted, and so it is possible that some reference
counts will never go to zero.
In the Set message, the Number of Fields value describes the number of repeated field selector entries in the
remainder of the message. If this number is less than the number of fields supported by the ONU, the message is
assumed to apply to the first N fields. The Reference Count field of the message is ignored in Set messages, and
should be set to zero. At the ONU, the field selector will be reprogrammed according to the layer select, dword
offset, bit offset, and bit width for any field that is not in use when the Set message is processed. Fields with nonzero
reference count will be ignored but the Set message will still return successfully.
The Set message format allows programming the fields on a per-port basis. However the set of field descriptors
in the upstream direction for both UNI ports will be treated as a single set of field descriptions. So programming a
field for either UNI port will also change the field selector for the other UNI port. Similarly, rules applied on one
UNI port will mean that the field is in use and unavailable to be reprogrammed for the other UNI port on the
ONU."
		::=  {  ucOnuRulesEntry  8  }
                                            
                                            
                                            
                                            
-- ============================================================================================================                                            
-- ============================================================================================================
-- ============================================================================================================
-- Design for ONU port storm-protect (only exist row for 4-port or 8-port ONU)

	ucOnuPortStormTable	OBJECT-TYPE
		SYNTAX		SEQUENCE  OF  UcOnuPortStormEntry
		MAX-ACCESS	not-accessible
		STATUS		current
		DESCRIPTION	"Description"
		::=  { ucFrameFilter  10 }

	ucOnuPortStormEntry	OBJECT-TYPE
		SYNTAX		UcOnuPortStormEntry
		MAX-ACCESS	not-accessible
		STATUS		current
		DESCRIPTION	"Description"
		INDEX		{  ucOnuPortStormSlotIndex, 
		               ucOnuPortStormPonIndex, 
		               ucOnuPortStormOnuIndex, 
		               ucOnuPortStormPortIndex  
		            }
		::=  { ucOnuPortStormTable 1 }

	UcOnuPortStormEntry  ::=  SEQUENCE {
		ucOnuPortStormSlotIndex  Integer32,
		ucOnuPortStormPonIndex   Integer32,
		ucOnuPortStormOnuIndex   Integer32,
		ucOnuPortStormPortIndex  Integer32, 
		ucOnuPortStormUpType       INTEGER,
		ucOnuPortStormUpRate       INTEGER,
		ucOnuPortStormDnType       INTEGER,
		ucOnuPortStormDnRate       INTEGER
	}


	ucOnuPortStormSlotIndex	OBJECT-TYPE	
		SYNTAX			Integer32  ( 1 .. 16  ) 
		MAX-ACCESS		read-only
		STATUS			current
		DESCRIPTION		"Description."
		::=  {  ucOnuPortStormEntry  1  }


	ucOnuPortStormPonIndex	OBJECT-TYPE	
		SYNTAX			Integer32  ( 1 .. 32  ) 
		MAX-ACCESS		read-only
		STATUS			current
		DESCRIPTION		"Description."
		::=  {  ucOnuPortStormEntry  2  }


	ucOnuPortStormOnuIndex	OBJECT-TYPE	
		SYNTAX			Integer32  ( 1 .. 256  ) 
		MAX-ACCESS		read-only
		STATUS			current
		DESCRIPTION		"Description."
		::=  {  ucOnuPortStormEntry  3  }


	ucOnuPortStormPortIndex	OBJECT-TYPE	
		SYNTAX			Integer32  ( 1 .. 24  ) 
		MAX-ACCESS		read-only
		STATUS			current
		DESCRIPTION		"Description."
		::=  {  ucOnuPortStormEntry  4  }


	ucOnuPortStormUpType	OBJECT-TYPE	
		SYNTAX			INTEGER {
			upBcast(1),
			upBcast_Mcast(3),
			upBcast_Mcast_UnUcast(19),
			upBcast_Mcast_ResMcast_Ucast_UnUcast(31)
		}			
		MAX-ACCESS		read-write
		STATUS			current
		DESCRIPTION		"Descript what type of upstream frame need ONU to press"
		::=  {  ucOnuPortStormEntry  5  }
		
	ucOnuPortStormUpRate	OBJECT-TYPE	
		SYNTAX			INTEGER  (984 .. 250000) 
		MAX-ACCESS		read-write
		STATUS			current
		DESCRIPTION		"Rate from 984Kbps~250000Kbps, not line-scale,  Unit: Kbps"
		::=  {  ucOnuPortStormEntry  6  }
		
	ucOnuPortStormDnType	OBJECT-TYPE	
		SYNTAX			INTEGER {
			dnBcast(1),
			dnBcast_Mcast(3),
			dnBcast_Mcast_UnUcast(19),
			dnBcast_Mcast_ResMcast_Ucast_UnUcast(31)
		}			
		MAX-ACCESS		read-write
		STATUS			current
		DESCRIPTION		"Descript what type of upstream frame need ONU to press"
		::=  {  ucOnuPortStormEntry  7  }
		
	ucOnuPortStormDnRate	OBJECT-TYPE	
		SYNTAX			INTEGER  (984 .. 250000) 
		MAX-ACCESS		read-write
		STATUS			current
		DESCRIPTION		"Rate from 984Kbps~250000Kbps, not line-scale,  Unit: Kbps"
		::=  {  ucOnuPortStormEntry  8  }
						
-- ============================================================================================================
-- ============================================================================================================
-- ============================================================================================================		
		
		                                            
	ucIGMPProxyTable	OBJECT-TYPE
		SYNTAX		SEQUENCE  OF  UcIGMPProxyEntry
		MAX-ACCESS	not-accessible
		STATUS		current
		DESCRIPTION	"Description"
		::=  { ucIGMP  1 }

	ucIGMPProxyEntry	OBJECT-TYPE
		SYNTAX		UcIGMPProxyEntry
		MAX-ACCESS	not-accessible
		STATUS		current
		DESCRIPTION	"Description"
		INDEX		{  ucIGMPProxySlotIndex, ucIGMPProxyPonIndex  }
		::=  { ucIGMPProxyTable 1 }

	UcIGMPProxyEntry  ::=  SEQUENCE {
		ucIGMPProxySlotIndex  Integer32,
		ucIGMPProxyPonIndex  Integer32,
		ucIGMPProxyCtrl  DisplayString,
		ucIGMPProxyCACStatus  DisplayString,
		ucIGMPStatistics  DisplayString
		}


	ucIGMPProxySlotIndex	OBJECT-TYPE	
		SYNTAX			Integer32  ( 1 .. 16  ) 
		MAX-ACCESS		read-only
		STATUS			current
		DESCRIPTION		"Description."
		::=  {  ucIGMPProxyEntry  1  }


	ucIGMPProxyPonIndex	OBJECT-TYPE	
		SYNTAX			Integer32  ( 1 .. 32  ) 
		MAX-ACCESS		read-only
		STATUS			current
		DESCRIPTION		"Description."
		::=  {  ucIGMPProxyEntry  2  }


	ucIGMPProxyCtrl	OBJECT-TYPE	
		SYNTAX			DisplayString
		MAX-ACCESS		read-write
		STATUS			current
		DESCRIPTION		"Size     Description
2 Maximum IGMP Groups(Setting to 0 disables IGMP Proxy in the OLT)----Default(0)--Min(0)--Max(4096)
2 Robustness Count----Default(2)--Min(1)--Max(16)
2 Query Interval----Units(10 ms)--Default(12500)--Min(11)--Max(65535)
2 Query Response Timeout----Units(10 ms)--Default(1001)--Min(11)--Max(65534)
2 Query Message Maximum Response Time----Units(100 ms)--Default(100)--Min(1)--Max(255)
2 Startup Query Count----Default(2)--Min(0)--Max(16)
2 Startup Query Interval----Units(10 ms)--Default(3125)--Min(11)--Max(65535)
2 Last Member Query Count----Default(2)--Min(0)--Max(16)
2 Last Member Query Interval----Units(10 ms)--Default(110)--Min(11)--Max(65535)
2 Last Member Query Message Max. Resp. Time----Units(100 ms)--Default(10)--Min(1)--Max(255)
2 Retransmit Count ----Default(0)--Min(0)--Max(3)
2 Retransmit Interval ----Units(10 ms)--Default(1000)--Min(1)--Max(65535)
2 VLAN Tag(Setting 0 removes VLAN from IGMP Queries
   It is strongly recommended that the IGMP VLAN
   provisioning message be used in lieu of this field
   and that this field always be set to zero.)----Default(0)--Min(0)--Max(4095)
2 Number of IGMP Queues ----Default(4)--Min(1)--Max(10)
   IGMP SLA
4 Minimum Guaranteed Bandwidth ----Units(Kbps)--Default(100,000)--Min(256)--Max(1,000,000)
4 Maximum Allowed Bandwidth ----Units(Kbps)--Default(100,000)--Min(256)--Max(1,000,000)
2 Priority Level(1 = Sensitive, 0 = Tolerant) ----Default(0)--Min(0)--Max(1)
2 Max Burst Size ----Units(KBytes)--Default(2)--Min(1)--Max(256)
4 Source IP address in IGMP frames. This is an
   optional field (Firmware will handle messages
   without this field. In a future release, this field
   shall be made a required field)----Default(0.0.0.0)
2 Option Bits. This is an optional field (Firmware
   will handle messages without this field)
   Bit0: Enable IGMP Frame checksum validation
   Bit1: Enable IGMP IP Header checksum validation
   Bit2: Enable OLT terminates all IP multicast traffic on all VLANS regardless of whether a proxy instance is created for that VLAN or not.
   Bit2  Bit15: Reserved


Note: When the priority level is sensitive, the Minimum Guaranteed Bandwidth must be equal to the Maximum
Allowed Bandwidth."
		::=  {  ucIGMPProxyEntry  3  }


	ucIGMPProxyCACStatus	OBJECT-TYPE	
		SYNTAX			DisplayString  ( SIZE ( 0 .. 255  ) ) 
		MAX-ACCESS		read-only
		STATUS			current
		DESCRIPTION		"Size    Description
2 Number of entries included in the message----Default(0)--Min(0)--Max(8)
4 Bandwidth in use for VID. This field repeats count times.
   This field appears in this message in the same order as VLANs in the IGMP
   VLAN provisioning message.----Units(Kbps)--Default(0)--Min(0)--Max(1000000)


To determine how much of each VLAN is allocated into the FCFS pool:
Calculate how much of each VLANs bandwidth is in the FCFS pool by subtracting the minimum bandwidth
from the current bandwidth in use for that VLAN. If this value is less than zero, the VLAN is not using the FCFS
pool. If it is greater than zero, it is using that amount of the FCFS pool."
		::=  {  ucIGMPProxyEntry  4  }


	ucIGMPStatistics	OBJECT-TYPE	
		SYNTAX			DisplayString  ( SIZE ( 0 .. 255  ) ) 
		MAX-ACCESS		read-write
		STATUS			current
		DESCRIPTION		"Size    Name    Description
4 Flags(Bit 0: 1 = Clear after read)----Options flags
4 Intervals DOS protection enabled----The number of milliseconds that the IGMP DOS protection feature has been active.
4 Discarded packets----IGMP type packets that were sent to the OLT processor but discarded because the proxy wasnt interested in them.
   The following packets increment this statistic:(Upstream queries.Downstream reports.Downstream leaves.)
4 General queries received.----A downstream general query message has been received and processed by the OLT.
4 General queries transmitted ----Number of general query messages generated by the OLT.
4 Group specific query received: known group ----The OLT has received a group specific query from the network side and the proxy is currently forwarding the group.
4 Group specific query received: unknown group. ----The OLT has received a group specific query from the network side and the proxy is not currently forwarding the group.
4 Group specific query messages transmitted ----The number of group specific queries that the OLT has sent.
4 Join refused: Provisioned to reject. ----The CAC resolution process produced a zero for the amount of bandwidth used by the group so the OLT disallowed the join.
4 Join refused: Could not resolve network VID from EPON VID.----Multiple network VLANs map to the same PON side VLAN and the OLT was not able to use the CAC database to determine which network VID a group belonged to.
4 Join refused: FIFO allocation forced by previous join and no room on FIFO.----The OLT FIFO allocation algorithm was forced to pick a FIFO that did not have enough bandwidth left. [See IGMP technote.]
4 Join refused: CAC algorithm found bandwidth available but no FIFO had enough free space for the join.----The OLT FIFO allocation algorithm tried and failed to find a FIFO with enough free bandwidth for a particular join even though the CAC tracker decided there was enough bandwidth available. [See IGMP technote.]
4 Join refused: No room in FCFS pool ----The first come first serve bandwidth pool did not have enough room for the OLT to allow a join to occur.

   Note the order of VLANs here corresponds exactly with the order of VLANs given in the IGMP VLAN provisioning message.

4 IGMP join refused because no CAC bandwidth for VID 1 ----A join was refused because it would have exceeded the maximum provisioned bandwidth for the VLAN.
4 IGMP join refused because no CAC bandwidth for 2 ----A join was refused because it would have exceeded the maximum provisioned bandwidth for the VLAN.
4 IGMP join refused because no CAC bandwidth for 3 ----A join was refused because it would have exceeded the maximum provisioned bandwidth for the VLAN.
4 IGMP join refused because no CAC bandwidth for 4 ----A join was refused because it would have exceeded the maximum provisioned bandwidth for the VLAN.
4 IGMP join refused because no CAC bandwidth for 5 ----A join was refused because it would have exceeded the maximum provisioned bandwidth for the VLAN.
4 IGMP join refused because no CAC bandwidth for 6 ----A join was refused because it would have exceeded the maximum provisioned bandwidth for the VLAN.
4 IGMP join refused because no CAC bandwidth for 7 ----A join was refused because it would have exceeded the maximum provisioned bandwidth for the VLAN.
4 IGMP join refused because no CAC bandwidth for 8 ----A join was refused because it would have exceeded the maximum provisioned bandwidth for the VLAN.
4 IGMP Join Refused Too Many Groups; ----A join was refused because it would have caused the proxy to exceed the maximum number of groups to forward.
4 Instances Dos Protection Applied ----Number of times the IGMP DOS protection algorithm has been activated.
4 Invalid Messages ----The IGMP proxy message queue has received a message that it did not expect. The message was discarded as unprocessed.
4 Join During LMQ Sequence ----A join that occurred for a group while it was going through the Lmq sequence.
4 Join for group already joined ----The proxy sees a join for a group that it is already forwarding.
4 Join for group not already joined ----The proxy sees a join for a group that it is not forwarding.
4 Leaves for known group received ----The proxy sees a leave for a group that it is currently forwarding.
4 Leaves for unknown group received ----The proxy sees a leave for a group that it is not currently forwarding.
4 Leaves while in LMQ cycle ----A group was already in the last member query cycle when an additional leave was seen by the OLT proxy.
4 Leaves TX because general query timer expired. ----An upstream leave for a group was transmitted because a general query timer expired.
4 Leaves TX because group specific query timer expired. ----An upstream leave for a group was transmitted because a group specific query caused the last member query counter to decrement to zero.
4 Leave TX because proxy going down. ----The number of leaves sent because the IGMP proxy on the OLT was turned off.
4 Message allocation failures ----OLT IGMP proxy couldnt allocate a block in its block pool.
4 Message send failures ----OLT IGMP proxy couldnt enqueue a message to a task.
4 Report messages sent ----Number of upstream report messages the OLT IGMP proxy has sent upstream.
4 Reports sent in response to general query ----The number of reports the OLT has generated in response to a general query.
4 Reports sent in response to group specific query ----The number of reports the OLT has generated in response to a group specific query.
4 Timer creation failures ----The IGMP proxy was unable to create a timer.
4 Unknown messages ----The IGMP proxy received a frame with IGMP protocol type but it was not one of the types that the proxy knows how to process. The proxy can process IGMP V1 join,IGMP V2 join, IGMP leave, and IGMP query messages.
4 IGMP join failed because of no binary search table entries.----The OLT ran out of room for forwarding entries in its binary search table.
4 IGMP join refused because the group address was not in the range 224.0.0.0 239.255.255.255 ----The IGMP proxy will discard joins for group addresses that do not fall within the IP multicast range.
4 IGMP join ignored because the group address was in the range 224.0.0.0 -- 224.0.0.255 ----The IGMP proxy always forwards 224.0.0.0 224.0.0.255 so there is no need to perform any action upon receipt of a join in this range.



The IGMP proxy keeps track of a number of statistics that may be of interest to the host. Please note that
additional statistics may be added to this message in future releases so it would be wise not to have the host
validate the messages length.
Send this message with the 4 byte flags field. The response message will include the flags field."
		::=  {  ucIGMPProxyEntry  5  }

	ucIGMPPerVlanTable	OBJECT-TYPE
		SYNTAX		SEQUENCE  OF  UcIGMPPerVlanEntry
		MAX-ACCESS	not-accessible
		STATUS		current
		DESCRIPTION	"Description"
		::=  { ucIGMP  2 }

	ucIGMPPerVlanEntry	OBJECT-TYPE
		SYNTAX		UcIGMPPerVlanEntry
		MAX-ACCESS	not-accessible
		STATUS		current
		DESCRIPTION	"Description"
		INDEX		{  ucIGMPPerVlanSlotIndex, ucIGMPPerVlanPonIndex, ucIGMPPerVlanGroupIndex  }
		::=  { ucIGMPPerVlanTable 1 }

	UcIGMPPerVlanEntry  ::=  SEQUENCE {
		ucIGMPPerVlanSlotIndex  Integer32,
		ucIGMPPerVlanPonIndex  Integer32,
		ucIGMPPerVlanNetVlan  Integer32,
		ucIGMPPerVlanGroupIndex  Integer32,
		ucIGMPPerVlanGroupVlan  Integer32,
		ucIGMPPerVlanGroupIpDa  IpAddress
		}


	ucIGMPPerVlanSlotIndex	OBJECT-TYPE	
		SYNTAX			Integer32  ( 1 .. 16  ) 
		MAX-ACCESS		read-only
		STATUS			current
		DESCRIPTION		"Description."
		::=  {  ucIGMPPerVlanEntry  1  }


	ucIGMPPerVlanPonIndex	OBJECT-TYPE	
		SYNTAX			Integer32  ( 1 .. 32  ) 
		MAX-ACCESS		read-only
		STATUS			current
		DESCRIPTION		"Description."
		::=  {  ucIGMPPerVlanEntry  2  }


	ucIGMPPerVlanNetVlan	OBJECT-TYPE	
		SYNTAX			Integer32  ( 0 .. 65535  ) 
		MAX-ACCESS		read-write
		STATUS			current
		DESCRIPTION		"Description."
		::=  {  ucIGMPPerVlanEntry  3  }


	ucIGMPPerVlanGroupIndex	OBJECT-TYPE	
		SYNTAX			Integer32  ( 1 .. 180  ) 
		MAX-ACCESS		read-only
		STATUS			current
		DESCRIPTION		"Description."
		::=  {  ucIGMPPerVlanEntry  4  }


	ucIGMPPerVlanGroupVlan	OBJECT-TYPE	
		SYNTAX			Integer32  ( 0 .. 4095  ) 
		MAX-ACCESS		read-write
		STATUS			current
		DESCRIPTION		"Description."
		::=  {  ucIGMPPerVlanEntry  5  }


	ucIGMPPerVlanGroupIpDa	OBJECT-TYPE	
		SYNTAX			IpAddress
		MAX-ACCESS		read-write
		STATUS			current
		DESCRIPTION		"Description."
		::=  {  ucIGMPPerVlanEntry  6  }

	ucIGMPVlanBWTable	OBJECT-TYPE
		SYNTAX		SEQUENCE  OF  UcIGMPVlanBWEntry
		MAX-ACCESS	not-accessible
		STATUS		current
		DESCRIPTION	"Description"
		::=  { ucIGMP  3 }

	ucIGMPVlanBWEntry	OBJECT-TYPE
		SYNTAX		UcIGMPVlanBWEntry
		MAX-ACCESS	not-accessible
		STATUS		current
		DESCRIPTION	"Description"
		INDEX		{  ucIGMPVlanBWSlotIndex, ucIGMPVlanBWPonIndex, ucIGMPVlanBWGroupIndex  }
		::=  { ucIGMPVlanBWTable 1 }

	UcIGMPVlanBWEntry  ::=  SEQUENCE {
		ucIGMPVlanBWSlotIndex  Integer32,
		ucIGMPVlanBWPonIndex  Integer32,
		ucIGMPVlanBWNetWorkVID  Integer32,
		ucIGMPVlanBWGroupIndex  Integer32,
		ucIGMPVlanBWGroupAddress  IpAddress,
		ucIGMPVlanBWGroupBW  Integer32
		}


	ucIGMPVlanBWSlotIndex	OBJECT-TYPE	
		SYNTAX			Integer32  ( 1 .. 16  ) 
		MAX-ACCESS		read-only
		STATUS			current
		DESCRIPTION		"Description."
		::=  {  ucIGMPVlanBWEntry  1  }


	ucIGMPVlanBWPonIndex	OBJECT-TYPE	
		SYNTAX			Integer32  ( 1 .. 32  ) 
		MAX-ACCESS		read-only
		STATUS			current
		DESCRIPTION		"Description."
		::=  {  ucIGMPVlanBWEntry  2  }


	ucIGMPVlanBWNetWorkVID	OBJECT-TYPE	
		SYNTAX			Integer32  ( 0 .. 4094  ) 
		MAX-ACCESS		read-write
		STATUS			current
		DESCRIPTION		"Description."
		::=  {  ucIGMPVlanBWEntry  3  }


	ucIGMPVlanBWGroupIndex	OBJECT-TYPE	
		SYNTAX			Integer32  ( 1 .. 180  ) 
		MAX-ACCESS		read-only
		STATUS			current
		DESCRIPTION		"Description."
		::=  {  ucIGMPVlanBWEntry  4  }


	ucIGMPVlanBWGroupAddress	OBJECT-TYPE	
		SYNTAX			IpAddress
		MAX-ACCESS		read-write
		STATUS			current
		DESCRIPTION		"Description."
		::=  {  ucIGMPVlanBWEntry  5  }


	ucIGMPVlanBWGroupBW	OBJECT-TYPE	
		SYNTAX			Integer32  ( 1 .. 1000  ) 
		MAX-ACCESS		read-write
		STATUS			current
		DESCRIPTION		"Description."
		::=  {  ucIGMPVlanBWEntry  6  }

	ucIGMPVlanProvisionTable	OBJECT-TYPE
		SYNTAX		SEQUENCE  OF  UcIGMPVlanProvisionEntry
		MAX-ACCESS	not-accessible
		STATUS		current
		DESCRIPTION	"Description"
		::=  { ucIGMP  4 }

	ucIGMPVlanProvisionEntry	OBJECT-TYPE
		SYNTAX		UcIGMPVlanProvisionEntry
		MAX-ACCESS	not-accessible
		STATUS		current
		DESCRIPTION	"Description"
		INDEX		{  ucIGMPVlanProvSlotIndex, ucIGMPVlanProvPonIndex, ucIGMPVlanProvGroupsIndex  }
		::=  { ucIGMPVlanProvisionTable 1 }

	UcIGMPVlanProvisionEntry  ::=  SEQUENCE {
		ucIGMPVlanProvSlotIndex  Integer32,
		ucIGMPVlanProvPonIndex  Integer32,
		ucIGMPVlanProvGroupsIndex  Integer32,
		ucIGMPVlanProvNetworkVID  Integer32,
		ucIGMPVlanProvEPONVID  Integer32,
		ucIGMPVlanProvVlanBW  Integer32,
		ucVidBwAlarmSetLevel  Integer32,
		ucVidBwAlarmClearLevel  Integer32
		}


	ucIGMPVlanProvSlotIndex	OBJECT-TYPE	
		SYNTAX			Integer32  ( 1 .. 16  ) 
		MAX-ACCESS		read-only
		STATUS			current
		DESCRIPTION		"Description."
		::=  {  ucIGMPVlanProvisionEntry  1  }


	ucIGMPVlanProvPonIndex	OBJECT-TYPE	
		SYNTAX			Integer32  ( 1 .. 32  ) 
		MAX-ACCESS		read-only
		STATUS			current
		DESCRIPTION		"Description."
		::=  {  ucIGMPVlanProvisionEntry  2  }


	ucIGMPVlanProvGroupsIndex	OBJECT-TYPE	
		SYNTAX			Integer32  ( 1 .. 8  ) 
		MAX-ACCESS		read-only
		STATUS			current
		DESCRIPTION		"Description."
		::=  {  ucIGMPVlanProvisionEntry  3  }


	ucIGMPVlanProvNetworkVID	OBJECT-TYPE	
		SYNTAX			Integer32  ( 0 .. 4095  ) 
		MAX-ACCESS		read-write
		STATUS			current
		DESCRIPTION		"Description."
		::=  {  ucIGMPVlanProvisionEntry  4  }


	ucIGMPVlanProvEPONVID	OBJECT-TYPE	
		SYNTAX			Integer32  ( 0 .. 4095  ) 
		MAX-ACCESS		read-write
		STATUS			current
		DESCRIPTION		"Description."
		::=  {  ucIGMPVlanProvisionEntry  5  }


	ucIGMPVlanProvVlanBW	OBJECT-TYPE	
		SYNTAX			Integer32  ( 0 .. 1000000  ) 
		MAX-ACCESS		read-write
		STATUS			current
		DESCRIPTION		"Description."
		::=  {  ucIGMPVlanProvisionEntry  6  }


	ucVidBwAlarmSetLevel	OBJECT-TYPE	
		SYNTAX			Integer32  ( 0 .. 1000000  ) 
		MAX-ACCESS		read-write
		STATUS			current
		DESCRIPTION		"Description."
		::=  {  ucIGMPVlanProvisionEntry  7  }


	ucVidBwAlarmClearLevel	OBJECT-TYPE	
		SYNTAX			Integer32  ( 0 .. 1000000  ) 
		MAX-ACCESS		read-write
		STATUS			current
		DESCRIPTION		"Description."
		::=  {  ucIGMPVlanProvisionEntry  8  }

	ucIGMPGroupTable	OBJECT-TYPE
		SYNTAX		SEQUENCE  OF  UcIGMPGroupEntry
		MAX-ACCESS	not-accessible
		STATUS		current
		DESCRIPTION	"Description"
		::=  { ucIGMP  5 }

	ucIGMPGroupEntry	OBJECT-TYPE
		SYNTAX		UcIGMPGroupEntry
		MAX-ACCESS	not-accessible
		STATUS		current
		DESCRIPTION	"Description"
		INDEX		{  ucIGMPGroupSlotIndex, ucIGMPGroupPonIndex, ucIGMPGroupIndex  }
		::=  { ucIGMPGroupTable 1 }

	UcIGMPGroupEntry  ::=  SEQUENCE {
		ucIGMPGroupSlotIndex  Integer32,
		ucIGMPGroupPonIndex  Integer32,
		ucIGMPGroupIndex  Integer32,
		ucIGMPGroupNetworkVID  Integer32,
		ucIGMPGroupIpDA  IpAddress
		}


	ucIGMPGroupSlotIndex	OBJECT-TYPE	
		SYNTAX			Integer32  ( 1 .. 16  ) 
		MAX-ACCESS		read-only
		STATUS			current
		DESCRIPTION		"Description."
		::=  {  ucIGMPGroupEntry  1  }


	ucIGMPGroupPonIndex	OBJECT-TYPE	
		SYNTAX			Integer32  ( 1 .. 32  ) 
		MAX-ACCESS		read-only
		STATUS			current
		DESCRIPTION		"Description."
		::=  {  ucIGMPGroupEntry  2  }


	ucIGMPGroupIndex	OBJECT-TYPE	
		SYNTAX			Integer32  ( 1 .. 180  ) 
		MAX-ACCESS		read-only
		STATUS			current
		DESCRIPTION		"Description."
		::=  {  ucIGMPGroupEntry  3  }


	ucIGMPGroupNetworkVID	OBJECT-TYPE	
		SYNTAX			Integer32  ( 0 .. 4095  ) 
		MAX-ACCESS		read-only
		STATUS			current
		DESCRIPTION		"Description."
		::=  {  ucIGMPGroupEntry  4  }


	ucIGMPGroupIpDA	OBJECT-TYPE	
		SYNTAX			IpAddress
		MAX-ACCESS		read-only
		STATUS			current
		DESCRIPTION		"Description."
		::=  {  ucIGMPGroupEntry  5  }

	ucOnuIGMPSnoopTable	OBJECT-TYPE
		SYNTAX		SEQUENCE  OF  UcOnuIGMPSnoopEntry
		MAX-ACCESS	not-accessible
		STATUS		current
		DESCRIPTION	"Description"
		::=  { ucIGMP  7 }

	ucOnuIGMPSnoopEntry	OBJECT-TYPE
		SYNTAX		UcOnuIGMPSnoopEntry
		MAX-ACCESS	not-accessible
		STATUS		current
		DESCRIPTION	"Description"
		INDEX		{  ucIGMPSnoopSlotIndex, ucIGMPSnoopPonIndex, ucIGMPSnoopOnuIndex, ucIGMPSnoopPortIndex  }
		::=  { ucOnuIGMPSnoopTable 1 }

	UcOnuIGMPSnoopEntry  ::=  SEQUENCE {
		ucIGMPSnoopSlotIndex  Integer32,
		ucIGMPSnoopPonIndex  Integer32,
		ucIGMPSnoopOnuIndex  Integer32,
		ucIGMPSnoopPortIndex  Integer32,
		ucIGMPSnoopIGMPGrps  Integer32,
		ucIGMPSnoopFwQByL2DA  INTEGER,
		ucIGMPSnoopFwQByVID  INTEGER,
		ucIGMPSnoopFwQByIpDA  INTEGER,
		ucIGMPSnoopFwQByIpSA  INTEGER,
		ucIGMPSnoopFwQByLink  INTEGER,
		ucIGMPSnoopDisableToCpuDn  INTEGER,
		ucIGMPSnoopDisableToCpuUp  INTEGER
		}


	ucIGMPSnoopSlotIndex	OBJECT-TYPE	
		SYNTAX			Integer32  ( 1 .. 16  ) 
		MAX-ACCESS		read-only
		STATUS			current
		DESCRIPTION		"Description."
		::=  {  ucOnuIGMPSnoopEntry  1  }


	ucIGMPSnoopPonIndex	OBJECT-TYPE	
		SYNTAX			Integer32  ( 1 .. 32  ) 
		MAX-ACCESS		read-only
		STATUS			current
		DESCRIPTION		"Description."
		::=  {  ucOnuIGMPSnoopEntry  2  }


	ucIGMPSnoopOnuIndex	OBJECT-TYPE	
		SYNTAX			Integer32  ( 1 .. 256  ) 
		MAX-ACCESS		read-only
		STATUS			current
		DESCRIPTION		"Description."
		::=  {  ucOnuIGMPSnoopEntry  3  }


	ucIGMPSnoopPortIndex	OBJECT-TYPE	
		SYNTAX			Integer32  ( 1 .. 24  ) 
		MAX-ACCESS		read-only
		STATUS			current
		DESCRIPTION		"Description."
		::=  {  ucOnuIGMPSnoopEntry  4  }


	ucIGMPSnoopIGMPGrps	OBJECT-TYPE	
		SYNTAX			Integer32  ( 0 .. 255  ) 
		MAX-ACCESS		read-write
		STATUS			current
		DESCRIPTION		"Description."
		::=  {  ucOnuIGMPSnoopEntry  5  }


	ucIGMPSnoopFwQByL2DA	OBJECT-TYPE	
		SYNTAX			INTEGER  { disable ( 1 ) , enable ( 2 ) } 
		MAX-ACCESS		read-write
		STATUS			current
		DESCRIPTION		"Description."
		::=  {  ucOnuIGMPSnoopEntry  6  }


	ucIGMPSnoopFwQByVID	OBJECT-TYPE	
		SYNTAX			INTEGER  { disable ( 1 ) , enable ( 2 ) } 
		MAX-ACCESS		read-write
		STATUS			current
		DESCRIPTION		"Description."
		::=  {  ucOnuIGMPSnoopEntry  7  }


	ucIGMPSnoopFwQByIpDA	OBJECT-TYPE	
		SYNTAX			INTEGER  { disable ( 1 ) , enable ( 2 ) } 
		MAX-ACCESS		read-write
		STATUS			current
		DESCRIPTION		"Description."
		::=  {  ucOnuIGMPSnoopEntry  8  }


	ucIGMPSnoopFwQByIpSA	OBJECT-TYPE	
		SYNTAX			INTEGER  { disable ( 1 ) , enable ( 2 ) } 
		MAX-ACCESS		read-write
		STATUS			current
		DESCRIPTION		"Description."
		::=  {  ucOnuIGMPSnoopEntry  9  }


	ucIGMPSnoopFwQByLink	OBJECT-TYPE	
		SYNTAX			INTEGER  { disable ( 1 ) , enable ( 2 ) } 
		MAX-ACCESS		read-write
		STATUS			current
		DESCRIPTION		"Description."
		::=  {  ucOnuIGMPSnoopEntry  10  }


	ucIGMPSnoopDisableToCpuDn	OBJECT-TYPE	
		SYNTAX			INTEGER  { true ( 1 ) , false ( 2 ) } 
		MAX-ACCESS		read-write
		STATUS			current
		DESCRIPTION		"Description."
		::=  {  ucOnuIGMPSnoopEntry  11  }


	ucIGMPSnoopDisableToCpuUp	OBJECT-TYPE	
		SYNTAX			INTEGER  { true ( 1 ) , false ( 2 ) } 
		MAX-ACCESS		read-write
		STATUS			current
		DESCRIPTION		"Description."
		::=  {  ucOnuIGMPSnoopEntry  12  }

	ucOnuIGMPGrpsTable	OBJECT-TYPE
		SYNTAX		SEQUENCE  OF  UcOnuIGMPGrpsEntry
		MAX-ACCESS	not-accessible
		STATUS		current
		DESCRIPTION	"Description"
		::=  { ucIGMP  8 }

	ucOnuIGMPGrpsEntry	OBJECT-TYPE
		SYNTAX		UcOnuIGMPGrpsEntry
		MAX-ACCESS	not-accessible
		STATUS		current
		DESCRIPTION	"Description"
		INDEX		{  ucOnuIGMPGrpsSlotIndex, ucOnuIGMPGrpsPonIndex, ucOnuIGMPGrpsOnuIndex  }
		::=  { ucOnuIGMPGrpsTable 1 }

	UcOnuIGMPGrpsEntry  ::=  SEQUENCE {
		ucOnuIGMPGrpsSlotIndex  Integer32,
		ucOnuIGMPGrpsPonIndex  Integer32,
		ucOnuIGMPGrpsOnuIndex  Integer32,
		ucOnuIGMPGrpsIp  IpAddress,
		ucOnuIGMPGrpsPortsBmp  Integer32
		}


	ucOnuIGMPGrpsSlotIndex	OBJECT-TYPE	
		SYNTAX			Integer32  ( 1 .. 16  ) 
		MAX-ACCESS		read-only
		STATUS			current
		DESCRIPTION		"Description."
		::=  {  ucOnuIGMPGrpsEntry  1  }


	ucOnuIGMPGrpsPonIndex	OBJECT-TYPE	
		SYNTAX			Integer32  ( 1 .. 32  ) 
		MAX-ACCESS		read-only
		STATUS			current
		DESCRIPTION		"Description."
		::=  {  ucOnuIGMPGrpsEntry  2  }


	ucOnuIGMPGrpsOnuIndex	OBJECT-TYPE	
		SYNTAX			Integer32  ( 1 .. 256  ) 
		MAX-ACCESS		read-only
		STATUS			current
		DESCRIPTION		"Description."
		::=  {  ucOnuIGMPGrpsEntry  3  }


	ucOnuIGMPGrpsIp	OBJECT-TYPE	
		SYNTAX			IpAddress
		MAX-ACCESS		read-write
		STATUS			current
		DESCRIPTION		"Description."
		::=  {  ucOnuIGMPGrpsEntry  4  }


	ucOnuIGMPGrpsPortsBmp	OBJECT-TYPE	
		SYNTAX			Integer32  ( 0 .. 255  ) 
		MAX-ACCESS		read-write
		STATUS			current
		DESCRIPTION		"Description."
		::=  {  ucOnuIGMPGrpsEntry  5  }

	ucOnuIGMPVlanProvTable	OBJECT-TYPE
		SYNTAX		SEQUENCE  OF  UcOnuIGMPVlanProvEntry
		MAX-ACCESS	not-accessible
		STATUS		current
		DESCRIPTION	"Description"
		::=  { ucIGMP  9 }

	ucOnuIGMPVlanProvEntry	OBJECT-TYPE
		SYNTAX		UcOnuIGMPVlanProvEntry
		MAX-ACCESS	not-accessible
		STATUS		current
		DESCRIPTION	"Description"
		INDEX		{  ucOnuIGMPVlanProvSlotIndex, ucOnuIGMPVlanProvPonIndex, ucOnuIGMPVlanProvOnuIndex  }
		::=  { ucOnuIGMPVlanProvTable 1 }

	UcOnuIGMPVlanProvEntry  ::=  SEQUENCE {
		ucOnuIGMPVlanProvSlotIndex  Integer32,
		ucOnuIGMPVlanProvPonIndex  Integer32,
		ucOnuIGMPVlanProvOnuIndex  Integer32,
		ucOnuIGMPVlanProvAction  INTEGER,
		ucOnuIGMPVlanProvVlanIndex  Integer32,
		ucOnuIGMPVlanProvEponVID  Integer32,
		ucOnuIGMPVlanProvUserVID  Integer32,
		ucOnuIGMPVlanProvMaxGrps  Integer32
		}


	ucOnuIGMPVlanProvSlotIndex	OBJECT-TYPE	
		SYNTAX			Integer32  ( 1 .. 16  ) 
		MAX-ACCESS		read-only
		STATUS			current
		DESCRIPTION		"Description."
		::=  {  ucOnuIGMPVlanProvEntry  1  }


	ucOnuIGMPVlanProvPonIndex	OBJECT-TYPE	
		SYNTAX			Integer32  ( 1 .. 32  ) 
		MAX-ACCESS		read-only
		STATUS			current
		DESCRIPTION		"Description."
		::=  {  ucOnuIGMPVlanProvEntry  2  }


	ucOnuIGMPVlanProvOnuIndex	OBJECT-TYPE	
		SYNTAX			Integer32  ( 1 .. 256  ) 
		MAX-ACCESS		read-only
		STATUS			current
		DESCRIPTION		"Description."
		::=  {  ucOnuIGMPVlanProvEntry  3  }


	ucOnuIGMPVlanProvAction	OBJECT-TYPE	
		SYNTAX			INTEGER  { discard ( 1 ) , ignore ( 2 ) } 
		MAX-ACCESS		read-write
		STATUS			current
		DESCRIPTION		"Description."
		::=  {  ucOnuIGMPVlanProvEntry  4  }


	ucOnuIGMPVlanProvVlanIndex	OBJECT-TYPE	
		SYNTAX			Integer32  ( 0 .. 16  ) 
		MAX-ACCESS		read-write
		STATUS			current
		DESCRIPTION		"Description."
		::=  {  ucOnuIGMPVlanProvEntry  5  }


	ucOnuIGMPVlanProvEponVID	OBJECT-TYPE	
		SYNTAX			Integer32  ( 0 .. 4095  ) 
		MAX-ACCESS		read-write
		STATUS			current
		DESCRIPTION		"Description."
		::=  {  ucOnuIGMPVlanProvEntry  6  }


	ucOnuIGMPVlanProvUserVID	OBJECT-TYPE	
		SYNTAX			Integer32  ( 0 .. 4095  ) 
		MAX-ACCESS		read-write
		STATUS			current
		DESCRIPTION		"Description."
		::=  {  ucOnuIGMPVlanProvEntry  7  }


	ucOnuIGMPVlanProvMaxGrps	OBJECT-TYPE	
		SYNTAX			Integer32  ( 0 .. 255  ) 
		MAX-ACCESS		read-write
		STATUS			current
		DESCRIPTION		"Description."
		::=  {  ucOnuIGMPVlanProvEntry  8  }

	ucEncryptTable	OBJECT-TYPE
		SYNTAX		SEQUENCE  OF  UcEncryptEntry
		MAX-ACCESS	not-accessible
		STATUS		current
		DESCRIPTION	"Description"
		::=  { ucSysFunc  1 }

	ucEncryptEntry	OBJECT-TYPE
		SYNTAX		UcEncryptEntry
		MAX-ACCESS	not-accessible
		STATUS		current
		DESCRIPTION	"Description"
		INDEX		{  ucEncodeSlotIndex, ucEncodePonIndex, ucEncodeOnuIndex  }
		::=  { ucEncryptTable 1 }

	UcEncryptEntry  ::=  SEQUENCE {
		ucEncodeSlotIndex  Integer32,
		ucEncodePonIndex  Integer32,
		ucEncodeOnuIndex  Integer32,
		ucEncodeLLID  DisplayString,
		ucEncodeMode  INTEGER,
		ucEncodeTimeout  Integer32
		}


	ucEncodeSlotIndex	OBJECT-TYPE	
		SYNTAX			Integer32  ( 1 .. 16  ) 
		MAX-ACCESS		read-only
		STATUS			current
		DESCRIPTION		"Description."
		::=  {  ucEncryptEntry  1  }


	ucEncodePonIndex	OBJECT-TYPE	
		SYNTAX			Integer32  ( 1 .. 32  ) 
		MAX-ACCESS		read-only
		STATUS			current
		DESCRIPTION		"Description."
		::=  {  ucEncryptEntry  2  }


	ucEncodeOnuIndex	OBJECT-TYPE	
		SYNTAX			Integer32  ( 1 .. 256  ) 
		MAX-ACCESS		read-only
		STATUS			current
		DESCRIPTION		"Description."
		::=  {  ucEncryptEntry  3  }


	ucEncodeLLID	OBJECT-TYPE	
		SYNTAX			DisplayString  ( SIZE ( 12 .. 12  ) ) 
		MAX-ACCESS		read-write
		STATUS			current
		DESCRIPTION		"Description."
		::=  {  ucEncryptEntry  4  }


	ucEncodeMode	OBJECT-TYPE	
		SYNTAX			INTEGER  { none ( 1 ) , aes128CFB ( 2 ) , aes128CTR ( 3 ) , churning ( 4 ) , tripleChurning ( 5 ) } 
		MAX-ACCESS		read-write
		STATUS			current
		DESCRIPTION		"Description."
		::=  {  ucEncryptEntry  5  }


	ucEncodeTimeout	OBJECT-TYPE	
		SYNTAX			Integer32  ( 0 .. 65535  ) 
		MAX-ACCESS		read-write
		STATUS			current
		DESCRIPTION		"Description."
		::=  {  ucEncryptEntry  6  }

	ucSyswareOltTable	OBJECT-TYPE
		SYNTAX		SEQUENCE  OF  UcSyswareOltEntry
		MAX-ACCESS	not-accessible
		STATUS		current
		DESCRIPTION	"Description"
		::=  { ucSysware  1 }

	ucSyswareOltEntry	OBJECT-TYPE
		SYNTAX		UcSyswareOltEntry
		MAX-ACCESS	not-accessible
		STATUS		current
		DESCRIPTION	"Description"
		INDEX		{  ucSyswareOltSlotIndex  }
		::=  { ucSyswareOltTable 1 }

	UcSyswareOltEntry  ::=  SEQUENCE {
		ucSyswareOltSlotIndex  Integer32,
		ucSyswareOltType  INTEGER,
		ucSyswareOltFileSize  Integer32,
		ucSyswareOltFilePath  DisplayString,
		ucSyswareOltState  INTEGER
		}


	ucSyswareOltSlotIndex	OBJECT-TYPE	
		SYNTAX			Integer32  ( 1 .. 16  ) 
		MAX-ACCESS		read-only
		STATUS			current
		DESCRIPTION		"Description."
		::=  {  ucSyswareOltEntry  1  }


	ucSyswareOltType	OBJECT-TYPE	
		SYNTAX			INTEGER  { none ( 1 ) , boot ( 2 ) , app ( 3 ) , personility ( 4 ) , all ( 5 ) } 
		MAX-ACCESS		read-write
		STATUS			current
		DESCRIPTION		"Description."
		::=  {  ucSyswareOltEntry  2  }


	ucSyswareOltFileSize	OBJECT-TYPE	
		SYNTAX			Integer32  ( 0 .. 4096  ) 
		MAX-ACCESS		read-write
		STATUS			current
		DESCRIPTION		"Description."
		::=  {  ucSyswareOltEntry  3  }


	ucSyswareOltFilePath	OBJECT-TYPE	
		SYNTAX			DisplayString
		MAX-ACCESS		read-write
		STATUS			current
		DESCRIPTION		"Description."
		::=  {  ucSyswareOltEntry  4  }


	ucSyswareOltState	OBJECT-TYPE	
		SYNTAX			INTEGER  { running ( 1 ) , updating ( 2 ) } 
		MAX-ACCESS		read-write
		STATUS			current
		DESCRIPTION		"Description."
		::=  {  ucSyswareOltEntry  5  }

	ucSyswareOnuTable	OBJECT-TYPE
		SYNTAX		SEQUENCE  OF  UcSyswareOnuEntry
		MAX-ACCESS	not-accessible
		STATUS		current
		DESCRIPTION	"Description"
		::=  { ucSysware  2 }

	ucSyswareOnuEntry	OBJECT-TYPE
		SYNTAX		UcSyswareOnuEntry
		MAX-ACCESS	not-accessible
		STATUS		current
		DESCRIPTION	"Description"
		INDEX		{  ucSyswareOnuSlotIndex, ucSyswareOnuPonIndex  }
		::=  { ucSyswareOnuTable 1 }

	UcSyswareOnuEntry  ::=  SEQUENCE {
		ucSyswareOnuSlotIndex  Integer32,
		ucSyswareOnuPonIndex  Integer32,
		ucSyswareOnuType  INTEGER,
		ucSyswareOnuFileSize  Integer32,
		ucSyswareOnuFilePath  DisplayString,
		ucSyswareOnuState  INTEGER
		}


	ucSyswareOnuSlotIndex	OBJECT-TYPE	
		SYNTAX			Integer32  ( 1 .. 16  ) 
		MAX-ACCESS		read-only
		STATUS			current
		DESCRIPTION		"Description."
		::=  {  ucSyswareOnuEntry  1  }


	ucSyswareOnuPonIndex	OBJECT-TYPE	
		SYNTAX			Integer32  ( 1 .. 32  ) 
		MAX-ACCESS		read-only
		STATUS			current
		DESCRIPTION		"Description."
		::=  {  ucSyswareOnuEntry  2  }


	ucSyswareOnuType	OBJECT-TYPE	
		SYNTAX			INTEGER  { none ( 1 ) , boot ( 2 ) , app ( 3 ) , personality ( 4 ) , all ( 5 ) } 
		MAX-ACCESS		read-write
		STATUS			current
		DESCRIPTION		"Description."
		::=  {  ucSyswareOnuEntry  3  }


	ucSyswareOnuFileSize	OBJECT-TYPE	
		SYNTAX			Integer32  ( 0 .. 4096  ) 
		MAX-ACCESS		read-write
		STATUS			current
		DESCRIPTION		"Description."
		::=  {  ucSyswareOnuEntry  4  }


	ucSyswareOnuFilePath	OBJECT-TYPE	
		SYNTAX			DisplayString
		MAX-ACCESS		read-write
		STATUS			current
		DESCRIPTION		"Description."
		::=  {  ucSyswareOnuEntry  5  }


	ucSyswareOnuState	OBJECT-TYPE	
		SYNTAX			INTEGER  { running ( 1 ) , updating ( 2 ) } 
		MAX-ACCESS		read-write
		STATUS			current
		DESCRIPTION		"Description."
		::=  {  ucSyswareOnuEntry  6  }

	ucSyswareNmsTable	OBJECT-TYPE
		SYNTAX		SEQUENCE  OF  UcSyswareNmsEntry
		MAX-ACCESS	not-accessible
		STATUS		current
		DESCRIPTION	""
		::=  { ucSysware  20 }

	ucSyswareNmsEntry	OBJECT-TYPE
		SYNTAX		UcSyswareNmsEntry
		MAX-ACCESS	not-accessible
		STATUS		current
		DESCRIPTION	""
		INDEX		{  ucNmsSlotIndex  }
		::=  { ucSyswareNmsTable 1 }

	UcSyswareNmsEntry  ::=  SEQUENCE {
		ucNmsSlotIndex  Integer32,
		ucNmsAuditAlarms  INTEGER,
		ucNmsAuditAlarmsPeriodMs  Integer32,
		ucNmsKeyExchangeTimerSec  Integer32,
		ucNmsAuthenticateLinks  INTEGER,
		ucNmsEnSLAOnLinkDiscovery  INTEGER,
		ucNmsEnOltAfterBoot  INTEGER,
		ucNmsEnVlanStuffOnOltEn  INTEGER,
		ucNmsSetKeyExchangeTimerOnDiscovery  INTEGER
		}


	ucNmsSlotIndex	OBJECT-TYPE	
		SYNTAX			Integer32  ( 1 .. 16  ) 
		MAX-ACCESS		read-only
		STATUS			current
		DESCRIPTION		"Description."
		::=  {  ucSyswareNmsEntry  1  }


	ucNmsAuditAlarms	OBJECT-TYPE	
		SYNTAX			INTEGER  { disabled ( 0 ) , enabled ( 1 ) } 
		MAX-ACCESS		read-write
		STATUS			current
		DESCRIPTION		"Description."
		::=  {  ucSyswareNmsEntry  2  }


	ucNmsAuditAlarmsPeriodMs	OBJECT-TYPE	
		SYNTAX			Integer32
		MAX-ACCESS		read-write
		STATUS			current
		DESCRIPTION		"Description."
		::=  {  ucSyswareNmsEntry  3  }


	ucNmsKeyExchangeTimerSec	OBJECT-TYPE	
		SYNTAX			Integer32
		MAX-ACCESS		read-write
		STATUS			current
		DESCRIPTION		"Description."
		::=  {  ucSyswareNmsEntry  4  }


	ucNmsAuthenticateLinks	OBJECT-TYPE	
		SYNTAX			INTEGER  { disabled ( 0 ) , enabled ( 1 ) } 
		MAX-ACCESS		read-write
		STATUS			current
		DESCRIPTION		"Description."
		::=  {  ucSyswareNmsEntry  5  }


	ucNmsEnSLAOnLinkDiscovery	OBJECT-TYPE	
		SYNTAX			INTEGER  { disabled ( 0 ) , enabled ( 1 ) } 
		MAX-ACCESS		read-write
		STATUS			current
		DESCRIPTION		"Description."
		::=  {  ucSyswareNmsEntry  6  }


	ucNmsEnOltAfterBoot	OBJECT-TYPE	
		SYNTAX			INTEGER  { disabled ( 0 ) , enabled ( 1 ) } 
		MAX-ACCESS		read-write
		STATUS			current
		DESCRIPTION		"Description."
		::=  {  ucSyswareNmsEntry  7  }


	ucNmsEnVlanStuffOnOltEn	OBJECT-TYPE	
		SYNTAX			INTEGER  { disabled ( 0 ) , enabled ( 1 ) } 
		MAX-ACCESS		read-write
		STATUS			current
		DESCRIPTION		"Description."
		::=  {  ucSyswareNmsEntry  8  }


	ucNmsSetKeyExchangeTimerOnDiscovery	OBJECT-TYPE	
		SYNTAX			INTEGER  { disabled ( 0 ) , enabled ( 1 ) } 
		MAX-ACCESS		read-write
		STATUS			current
		DESCRIPTION		"Description."
		::=  {  ucSyswareNmsEntry  9  }

	ucSecretsTable	OBJECT-TYPE
		SYNTAX		SEQUENCE  OF  UcSecretsEntry
		MAX-ACCESS	not-accessible
		STATUS		current
		DESCRIPTION	"Description"
		::=  { ucSysware  21 }

	ucSecretsEntry	OBJECT-TYPE
		SYNTAX		UcSecretsEntry
		MAX-ACCESS	not-accessible
		STATUS		current
		DESCRIPTION	"Description."
		INDEX		{  ucSecretsSlotIndex  }
		::=  { ucSecretsTable 1 }

	UcSecretsEntry  ::=  SEQUENCE {
		ucSecretsSlotIndex  Integer32,
		ucSecretsMac  DisplayString,
		ucSecretsSecret  DisplayString,
		ucSecretsOperation  INTEGER
		}


	ucSecretsSlotIndex	OBJECT-TYPE	
		SYNTAX			Integer32  ( 1 .. 16  ) 
		MAX-ACCESS		read-write
		STATUS			current
		DESCRIPTION		"Description."
		::=  {  ucSecretsEntry  1  }


	ucSecretsMac	OBJECT-TYPE	
		SYNTAX			DisplayString  ( SIZE ( 12 .. 12  ) ) 
		MAX-ACCESS		read-only
		STATUS			current
		DESCRIPTION		"Description."
		::=  {  ucSecretsEntry  2  }


	ucSecretsSecret	OBJECT-TYPE	
		SYNTAX			DisplayString  ( SIZE ( 256 .. 256  ) ) 
		MAX-ACCESS		read-write
		STATUS			current
		DESCRIPTION		"Description."
		::=  {  ucSecretsEntry  3  }


	ucSecretsOperation	OBJECT-TYPE	
		SYNTAX			INTEGER  { none ( 0 ) , add ( 1 ) , delete ( 2 ) } 
		MAX-ACCESS		read-write
		STATUS			current
		DESCRIPTION		"Description."
		::=  {  ucSecretsEntry  4  }

	ucLogFilePath	OBJECT-TYPE	
		SYNTAX			DisplayString
		MAX-ACCESS		read-only
		STATUS			current
		DESCRIPTION		"Description."
		::=  {  ucConfig  1  }

	ucLogFileSize	OBJECT-TYPE	
		SYNTAX			Integer32  ( 0 .. 2048  ) 
		MAX-ACCESS		read-write
		STATUS			current
		DESCRIPTION		"Description."
		::=  {  ucConfig  2  }

	ucStatOltTable	OBJECT-TYPE
		SYNTAX		SEQUENCE  OF  UcStatOltEntry
		MAX-ACCESS	not-accessible
		STATUS		current
		DESCRIPTION	"Description"
		::=  { ucPortStat  1 }

	ucStatOltEntry	OBJECT-TYPE
		SYNTAX		UcStatOltEntry
		MAX-ACCESS	not-accessible
		STATUS		current
		DESCRIPTION	"Description"
		INDEX		{  ucStatOltSlotIndex, ucStatOltPonIndex, ucStatOltPortIndex  }
		::=  { ucStatOltTable 1 }

	UcStatOltEntry  ::=  SEQUENCE {
		ucStatOltSlotIndex  Integer32,
		ucStatOltPonIndex  Integer32,
		ucStatOltPortIndex  Integer32,
		ucStatOltDownstream  DisplayString,
		ucStatOltUpstream  DisplayString,
		ucStatOltReset  INTEGER
		}


	ucStatOltSlotIndex	OBJECT-TYPE	
		SYNTAX			Integer32  ( 1 .. 16  ) 
		MAX-ACCESS		read-only
		STATUS			current
		DESCRIPTION		"Description."
		::=  {  ucStatOltEntry  1  }


	ucStatOltPonIndex	OBJECT-TYPE	
		SYNTAX			Integer32  ( 1 .. 32  ) 
		MAX-ACCESS		read-only
		STATUS			current
		DESCRIPTION		"Description."
		::=  {  ucStatOltEntry  2  }


	ucStatOltPortIndex	OBJECT-TYPE	
		SYNTAX			Integer32  ( 1 .. 24  ) 
		MAX-ACCESS		read-only
		STATUS			current
		DESCRIPTION		"Description."
		::=  {  ucStatOltEntry  3  }


	ucStatOltDownstream	OBJECT-TYPE	
		SYNTAX			DisplayString  ( SIZE ( 0 .. 384  ) ) 
		MAX-ACCESS		read-only
		STATUS			current
		DESCRIPTION		"size    Description
8    rxTxOctets
8    rxTxPkts
8    unicastPkts
8    bcstPkts
8    multiPkts
8    crcErrors
8    undersizeFrames
8    oversizeFrames
8    collisions
8    Frames64Octet
8    Frames65_127Octet
8    Frames128_255Octet
8    Frames256_511Octet
8    Frames512_1023Octet
8    Frames1024_1518Octet
8    FramesGreaterThan1518
8    droppedPkts
8    droppedBytes
8    delayedBytes
8    grantedBytes
8    grantedUnusedBytes
8    crc8Errors // preamble CRC errors
8    pauseFrames
8    lineCodeErr // line code violations"
		::=  {  ucStatOltEntry  4  }


	ucStatOltUpstream	OBJECT-TYPE	
		SYNTAX			DisplayString  ( SIZE ( 0 .. 384  ) ) 
		MAX-ACCESS		read-only
		STATUS			current
		DESCRIPTION		"size    Description
8    rxTxOctets
8    rxTxPkts
8    unicastPkts
8    bcstPkts
8    multiPkts
8    crcErrors
8    undersizeFrames
8    oversizeFrames
8    collisions
8    Frames64Octet
8    Frames65_127Octet
8    Frames128_255Octet
8    Frames256_511Octet
8    Frames512_1023Octet
8    Frames1024_1518Octet
8    FramesGreaterThan1518
8    droppedPkts
8    droppedBytes
8    delayedBytes
8    grantedBytes
8    grantedUnusedBytes
8    crc8Errors // preamble CRC errors
8    pauseFrames
8    lineCodeErr // line code violations"
		::=  {  ucStatOltEntry  5  }


	ucStatOltReset	OBJECT-TYPE	
		SYNTAX			INTEGER  { nop ( 0 ) , reset ( 1 ) } 
		MAX-ACCESS		read-write
		STATUS			current
		DESCRIPTION		"This command resets all statistics counts maintained at the OLT."
		::=  {  ucStatOltEntry  30  }

	ucStatOnuTable	OBJECT-TYPE
		SYNTAX		SEQUENCE  OF  UcStatOnuEntry
		MAX-ACCESS	not-accessible
		STATUS		current
		DESCRIPTION	"Description"
		::=  { ucPortStat  2 }

	ucStatOnuEntry	OBJECT-TYPE
		SYNTAX		UcStatOnuEntry
		MAX-ACCESS	not-accessible
		STATUS		current
		DESCRIPTION	"Description"
		INDEX		{  ucStatOnuSlotIndex, ucStatOnuPonIndex, ucStatOnuOnuIndex, ucStatOnuPortIndex  }
		::=  { ucStatOnuTable 1 }

	UcStatOnuEntry  ::=  SEQUENCE {
		ucStatOnuSlotIndex  Integer32,
		ucStatOnuPonIndex  Integer32,
		ucStatOnuOnuIndex  Integer32,
		ucStatOnuPortIndex  Integer32,
		ucStatOnuPortDownstream  DisplayString,
		ucStatOnuPortUpstream  DisplayString,
		ucStatOnuReset  INTEGER
		}


	ucStatOnuSlotIndex	OBJECT-TYPE	
		SYNTAX			Integer32  ( 1 .. 16  ) 
		MAX-ACCESS		read-only
		STATUS			current
		DESCRIPTION		""
		::=  {  ucStatOnuEntry  1  }


	ucStatOnuPonIndex	OBJECT-TYPE	
		SYNTAX			Integer32  ( 1 .. 32  ) 
		MAX-ACCESS		read-only
		STATUS			current
		DESCRIPTION		""
		::=  {  ucStatOnuEntry  2  }


	ucStatOnuOnuIndex	OBJECT-TYPE	
		SYNTAX			Integer32  ( 1 .. 256  ) 
		MAX-ACCESS		read-only
		STATUS			current
		DESCRIPTION		""
		::=  {  ucStatOnuEntry  3  }


	ucStatOnuPortIndex	OBJECT-TYPE	
		SYNTAX			Integer32  ( 1 .. 24  ) 
		MAX-ACCESS		read-only
		STATUS			current
		DESCRIPTION		""
		::=  {  ucStatOnuEntry  4  }


	ucStatOnuPortDownstream	OBJECT-TYPE	
		SYNTAX			DisplayString  ( SIZE ( 0 .. 384  ) ) 
		MAX-ACCESS		read-only
		STATUS			current
		DESCRIPTION		"size    Description
8    rxTxOctets
8    rxTxPkts
8    unicastPkts
8    bcstPkts
8    multiPkts
8    crcErrors
8    undersizeFrames
8    oversizeFrames
8    collisions
8    Frames64Octet
8    Frames65_127Octet
8    Frames128_255Octet
8    Frames256_511Octet
8    Frames512_1023Octet
8    Frames1024_1518Octet
8    FramesGreaterThan1518
8    droppedPkts
8    droppedBytes
8    delayedBytes
8    grantedBytes
8    grantedUnusedBytes
8    crc8Errors // preamble CRC errors
8    pauseFrames
8    lineCodeErr // line code violations"
		::=  {  ucStatOnuEntry  5  }


	ucStatOnuPortUpstream	OBJECT-TYPE	
		SYNTAX			DisplayString  ( SIZE ( 0 .. 384  ) ) 
		MAX-ACCESS		read-only
		STATUS			current
		DESCRIPTION		"size    Description
8    rxTxOctets
8    rxTxPkts
8    unicastPkts
8    bcstPkts
8    multiPkts
8    crcErrors
8    undersizeFrames
8    oversizeFrames
8    collisions
8    Frames64Octet
8    Frames65_127Octet
8    Frames128_255Octet
8    Frames256_511Octet
8    Frames512_1023Octet
8    Frames1024_1518Octet
8    FramesGreaterThan1518
8    droppedPkts
8    droppedBytes
8    delayedBytes
8    grantedBytes
8    grantedUnusedBytes
8    crc8Errors // preamble CRC errors
8    pauseFrames
8    lineCodeErr // line code violations"
		::=  {  ucStatOnuEntry  6  }


	ucStatOnuReset	OBJECT-TYPE	
		SYNTAX			INTEGER  { nop ( 0 ) , reset ( 1 ) } 
		MAX-ACCESS		read-write
		STATUS			current
		DESCRIPTION		"This command resets all statistic counts maintained at an ONU"
		::=  {  ucStatOnuEntry  31  }

	ucStatLLIDTable	OBJECT-TYPE
		SYNTAX		SEQUENCE  OF  UcStatLLIDEntry
		MAX-ACCESS	not-accessible
		STATUS		current
		DESCRIPTION	"Description"
		::=  { ucPortStat  4 }

	ucStatLLIDEntry	OBJECT-TYPE
		SYNTAX		UcStatLLIDEntry
		MAX-ACCESS	not-accessible
		STATUS		current
		DESCRIPTION	"Description"
		INDEX		{  ucStatLLIDSlotIndex, ucStatLLIDPonIndex, ucStatLLIDOnuIndex, ucStatLLIDLLIDIndex  }
		::=  { ucStatLLIDTable 1 }

	UcStatLLIDEntry  ::=  SEQUENCE {
		ucStatLLIDSlotIndex  Integer32,
		ucStatLLIDPonIndex  Integer32,
		ucStatLLIDOnuIndex  Integer32,
		ucStatLLIDLLIDIndex  Integer32,
		ucStatLLIDDownstream  DisplayString,
		ucStatLLIDUpstream  DisplayString,
		ucStatLLIDMpcpDownstream  DisplayString,
		ucStatLLIDMpcpUpstream  DisplayString,
		ucStatLLIDQueueDownstream  DisplayString,
		ucStatLLIDQueueUpstream  DisplayString,
		ucStatLLIDReset  INTEGER
		}


	ucStatLLIDSlotIndex	OBJECT-TYPE	
		SYNTAX			Integer32  ( 1 .. 16  ) 
		MAX-ACCESS		read-only
		STATUS			current
		DESCRIPTION		"Description."
		::=  {  ucStatLLIDEntry  1  }


	ucStatLLIDPonIndex	OBJECT-TYPE	
		SYNTAX			Integer32  ( 1 .. 32  ) 
		MAX-ACCESS		read-only
		STATUS			current
		DESCRIPTION		"Description."
		::=  {  ucStatLLIDEntry  2  }


	ucStatLLIDOnuIndex	OBJECT-TYPE	
		SYNTAX			Integer32  ( 1 .. 256  ) 
		MAX-ACCESS		read-only
		STATUS			current
		DESCRIPTION		"Description."
		::=  {  ucStatLLIDEntry  3  }


	ucStatLLIDLLIDIndex	OBJECT-TYPE	
		SYNTAX			Integer32  ( 0 .. 4096  ) 
		MAX-ACCESS		not-accessible
		STATUS			current
		DESCRIPTION		"Description."
		::=  {  ucStatLLIDEntry  4  }


	ucStatLLIDDownstream	OBJECT-TYPE	
		SYNTAX			DisplayString  ( SIZE ( 0 .. 255  ) ) 
		MAX-ACCESS		read-only
		STATUS			current
		DESCRIPTION		"size    Description
8    rxTxOctets
8    rxTxPkts
8    unicastPkts
8    bcstPkts
8    multiPkts
8    crcErrors
8    undersizeFrames
8    oversizeFrames
8    Frames64Octet
8    Frames65_127Octet
8    Frames128_255Octet
8    Frames256_511Octet
8    Frames512_1023Octet
8    Frames1024_1518Octet
8    Frames1519_1536Octet
8    droppedPkts
8    droppedBytes
8    delayedBytes
8    grantedBytes
8    grantedButUnusedBytes
8    maxDelay // Units of 100 us
8    lineCodeErrors);
8    errFrameSec // ONU stat
8    errFramePeriod // ONU stat
8    errFrameSecSummary // ONU stat"
		::=  {  ucStatLLIDEntry  5  }


	ucStatLLIDUpstream	OBJECT-TYPE	
		SYNTAX			DisplayString  ( SIZE ( 0 .. 255  ) ) 
		MAX-ACCESS		read-only
		STATUS			current
		DESCRIPTION		"size    Description
8    rxTxOctets
8    rxTxPkts
8    unicastPkts
8    bcstPkts
8    multiPkts
8    crcErrors
8    undersizeFrames
8    oversizeFrames
8    Frames64Octet
8    Frames65_127Octet
8    Frames128_255Octet
8    Frames256_511Octet
8    Frames512_1023Octet
8    Frames1024_1518Octet
8    Frames1519_1536Octet
8    droppedPkts
8    droppedBytes
8    delayedBytes
8    grantedBytes
8    grantedButUnusedBytes
8    maxDelay // Units of 100 us
8    lineCodeErrors);
8    errFrameSec // ONU stat
8    errFramePeriod // ONU stat
8    errFrameSecSummary // ONU stat"
		::=  {  ucStatLLIDEntry  6  }


	ucStatLLIDMpcpDownstream	OBJECT-TYPE	
		SYNTAX			DisplayString  ( SIZE ( 0 .. 255  ) ) 
		MAX-ACCESS		read-only
		STATUS			current
		DESCRIPTION		"size    Description
4    mpcpFrames
4    mpcpDiscoveryWindows
4    mpcpDiscoveryTimeout
4    mpcpRegisterRequests
4    mpcpRegisterAcks
4    mpcpRegisterReports
4    mpcpGates
4    mpcpRegisters"
		::=  {  ucStatLLIDEntry  7  }


	ucStatLLIDMpcpUpstream	OBJECT-TYPE	
		SYNTAX			DisplayString  ( SIZE ( 0 .. 255  ) ) 
		MAX-ACCESS		read-only
		STATUS			current
		DESCRIPTION		"size    Description
4    mpcpFrames
4    mpcpDiscoveryWindows
4    mpcpDiscoveryTimeout
4    mpcpRegisterRequests
4    mpcpRegisterAcks
4    mpcpRegisterReports
4    mpcpGates
4    mpcpRegisters"
		::=  {  ucStatLLIDEntry  8  }


	ucStatLLIDQueueDownstream	OBJECT-TYPE	
		SYNTAX			DisplayString  ( SIZE ( 0 .. 255  ) ) 
		MAX-ACCESS		read-only
		STATUS			current
		DESCRIPTION		"size    Description
8    rxTxOctets
8    rxTxPkts
8    droppedPkts
8    droppedBytes
8    delayedBytes
8    maxDelay"
		::=  {  ucStatLLIDEntry  9  }


	ucStatLLIDQueueUpstream	OBJECT-TYPE	
		SYNTAX			DisplayString  ( SIZE ( 0 .. 255  ) ) 
		MAX-ACCESS		read-only
		STATUS			current
		DESCRIPTION		"size    Description
8    rxTxOctets
8    rxTxPkts
8    droppedPkts
8    droppedBytes
8    delayedBytes
8    maxDelay"
		::=  {  ucStatLLIDEntry  10  }


	ucStatLLIDReset	OBJECT-TYPE	
		SYNTAX			INTEGER  { yes ( 1 ) , no ( 2 ) } 
		MAX-ACCESS		read-write
		STATUS			current
		DESCRIPTION		"This command resets all statistic counts maintained at an ONU."
		::=  {  ucStatLLIDEntry  32  }

	ucStatOltMpcpTable	OBJECT-TYPE
		SYNTAX		SEQUENCE  OF  UcStatOltMpcpEntry
		MAX-ACCESS	not-accessible
		STATUS		current
		DESCRIPTION	"Description"
		::=  { ucPortStat  5 }

	ucStatOltMpcpEntry	OBJECT-TYPE
		SYNTAX		UcStatOltMpcpEntry
		MAX-ACCESS	not-accessible
		STATUS		current
		DESCRIPTION	"Description"
		INDEX		{  ucStatOltMpcpSlotIndex, ucStatOltMpcpPonIndex  }
		::=  { ucStatOltMpcpTable 1 }

	UcStatOltMpcpEntry  ::=  SEQUENCE {
		ucStatOltMpcpSlotIndex  Integer32,
		ucStatOltMpcpPonIndex  Integer32,
		ucStatOltMpcpLLID  DisplayString,
		ucStatOltMpcpDir  INTEGER,
		ucStatOltMpcpFrames  Counter32,
		ucStatOltMpcpDiscoveryWinSent  Counter32,
		ucStatOltMpcpDiscoveryTout  Counter32,
		ucStatOltMpcpRegisterRequests  Counter32,
		ucStatOltMpcpRegisterAcks  Counter32,
		ucStatOltMpcpRegisterReports  Counter32,
		ucStatOltMpcpGates  Counter32,
		ucStatOltMpcpRegisters  Counter64,
		ucStatOltMpcpStatMode  INTEGER,
		ucStatOltMpcpReset  INTEGER
		}


	ucStatOltMpcpSlotIndex	OBJECT-TYPE	
		SYNTAX			Integer32  ( 1 .. 16  ) 
		MAX-ACCESS		read-only
		STATUS			current
		DESCRIPTION		"Description."
		::=  {  ucStatOltMpcpEntry  1  }


	ucStatOltMpcpPonIndex	OBJECT-TYPE	
		SYNTAX			Integer32  ( 1 .. 32  ) 
		MAX-ACCESS		read-only
		STATUS			current
		DESCRIPTION		"Description."
		::=  {  ucStatOltMpcpEntry  2  }


	ucStatOltMpcpLLID	OBJECT-TYPE	
		SYNTAX			DisplayString  ( SIZE ( 12 .. 12  ) ) 
		MAX-ACCESS		read-only
		STATUS			current
		DESCRIPTION		"Description."
		::=  {  ucStatOltMpcpEntry  3  }


	ucStatOltMpcpDir	OBJECT-TYPE	
		SYNTAX			INTEGER  { downstream ( 1 ) , upstream ( 2 ) } 
		MAX-ACCESS		read-only
		STATUS			current
		DESCRIPTION		"Description."
		::=  {  ucStatOltMpcpEntry  4  }


	ucStatOltMpcpFrames	OBJECT-TYPE	
		SYNTAX			Counter32
		MAX-ACCESS		read-only
		STATUS			current
		DESCRIPTION		"Description."
		::=  {  ucStatOltMpcpEntry  5  }


	ucStatOltMpcpDiscoveryWinSent	OBJECT-TYPE	
		SYNTAX			Counter32
		MAX-ACCESS		read-only
		STATUS			current
		DESCRIPTION		"Description."
		::=  {  ucStatOltMpcpEntry  6  }


	ucStatOltMpcpDiscoveryTout	OBJECT-TYPE	
		SYNTAX			Counter32
		MAX-ACCESS		read-only
		STATUS			current
		DESCRIPTION		"Description."
		::=  {  ucStatOltMpcpEntry  7  }


	ucStatOltMpcpRegisterRequests	OBJECT-TYPE	
		SYNTAX			Counter32
		MAX-ACCESS		read-only
		STATUS			current
		DESCRIPTION		"Description."
		::=  {  ucStatOltMpcpEntry  8  }


	ucStatOltMpcpRegisterAcks	OBJECT-TYPE	
		SYNTAX			Counter32
		MAX-ACCESS		read-only
		STATUS			current
		DESCRIPTION		"Description."
		::=  {  ucStatOltMpcpEntry  9  }


	ucStatOltMpcpRegisterReports	OBJECT-TYPE	
		SYNTAX			Counter32
		MAX-ACCESS		read-only
		STATUS			current
		DESCRIPTION		"Description."
		::=  {  ucStatOltMpcpEntry  10  }


	ucStatOltMpcpGates	OBJECT-TYPE	
		SYNTAX			Counter32
		MAX-ACCESS		read-only
		STATUS			current
		DESCRIPTION		"Description."
		::=  {  ucStatOltMpcpEntry  11  }


	ucStatOltMpcpRegisters	OBJECT-TYPE	
		SYNTAX			Counter64
		MAX-ACCESS		read-only
		STATUS			current
		DESCRIPTION		"Description."
		::=  {  ucStatOltMpcpEntry  12  }


	ucStatOltMpcpStatMode	OBJECT-TYPE	
		SYNTAX			INTEGER  { realtime ( 1 ) , avgPerMin15 ( 2 ) , avgPerDay ( 3 ) } 
		MAX-ACCESS		read-write
		STATUS			current
		DESCRIPTION		"Description."
		::=  {  ucStatOltMpcpEntry  13  }


	ucStatOltMpcpReset	OBJECT-TYPE	
		SYNTAX			INTEGER  { yes ( 1 ) , no ( 2 ) } 
		MAX-ACCESS		read-write
		STATUS			current
		DESCRIPTION		"Description."
		::=  {  ucStatOltMpcpEntry  14  }

	ucStatOnuMpcpTable	OBJECT-TYPE
		SYNTAX		SEQUENCE  OF  UcStatOnuMpcpEntry
		MAX-ACCESS	not-accessible
		STATUS		current
		DESCRIPTION	"Description"
		::=  { ucPortStat  6 }

	ucStatOnuMpcpEntry	OBJECT-TYPE
		SYNTAX		UcStatOnuMpcpEntry
		MAX-ACCESS	not-accessible
		STATUS		current
		DESCRIPTION	"Description"
		INDEX		{  ucStatOnuMpcpSlotIndex, ucStatOnuMpcpPonIndex, ucStatOnuMpcpOnuIndex  }
		::=  { ucStatOnuMpcpTable 1 }

	UcStatOnuMpcpEntry  ::=  SEQUENCE {
		ucStatOnuMpcpSlotIndex  Integer32,
		ucStatOnuMpcpPonIndex  Integer32,
		ucStatOnuMpcpOnuIndex  Integer32,
		ucStatOnuMpcpLLID  DisplayString,
		ucStatOnuMpcpDir  INTEGER,
		ucStatOnuMpcpFrames  Counter32,
		ucStatOnuMpcpDiscoveryWinSent  Counter32,
		ucStatOnuMpcpDiscoveryTout  Counter32,
		ucStatOnuMpcpRegisterRequests  Counter32,
		ucStatOnuMpcpRegisterAcks  Counter32,
		ucStatOnuMpcpRegisterReports  Counter32,
		ucStatOnuMpcpGates  Counter32,
		ucStatOnuMpcpRegisters  Counter32,
		ucStatOnuMpcpStatMode  INTEGER,
		ucStatOnuMpcpReset  INTEGER
		}


	ucStatOnuMpcpSlotIndex	OBJECT-TYPE	
		SYNTAX			Integer32  ( 1 .. 16  ) 
		MAX-ACCESS		read-only
		STATUS			current
		DESCRIPTION		"Description."
		::=  {  ucStatOnuMpcpEntry  1  }


	ucStatOnuMpcpPonIndex	OBJECT-TYPE	
		SYNTAX			Integer32  ( 1 .. 32  ) 
		MAX-ACCESS		read-only
		STATUS			current
		DESCRIPTION		"Description."
		::=  {  ucStatOnuMpcpEntry  2  }


	ucStatOnuMpcpOnuIndex	OBJECT-TYPE	
		SYNTAX			Integer32  ( 1 .. 256  ) 
		MAX-ACCESS		read-only
		STATUS			current
		DESCRIPTION		"Description."
		::=  {  ucStatOnuMpcpEntry  3  }


	ucStatOnuMpcpLLID	OBJECT-TYPE	
		SYNTAX			DisplayString  ( SIZE ( 12 .. 12  ) ) 
		MAX-ACCESS		read-only
		STATUS			current
		DESCRIPTION		"Description."
		::=  {  ucStatOnuMpcpEntry  4  }


	ucStatOnuMpcpDir	OBJECT-TYPE	
		SYNTAX			INTEGER  { downstream ( 1 ) , upstream ( 2 ) } 
		MAX-ACCESS		read-only
		STATUS			current
		DESCRIPTION		"Description."
		::=  {  ucStatOnuMpcpEntry  5  }


	ucStatOnuMpcpFrames	OBJECT-TYPE	
		SYNTAX			Counter32
		MAX-ACCESS		read-only
		STATUS			current
		DESCRIPTION		"Description."
		::=  {  ucStatOnuMpcpEntry  6  }


	ucStatOnuMpcpDiscoveryWinSent	OBJECT-TYPE	
		SYNTAX			Counter32
		MAX-ACCESS		read-only
		STATUS			current
		DESCRIPTION		"Description."
		::=  {  ucStatOnuMpcpEntry  7  }


	ucStatOnuMpcpDiscoveryTout	OBJECT-TYPE	
		SYNTAX			Counter32
		MAX-ACCESS		read-only
		STATUS			current
		DESCRIPTION		"Description."
		::=  {  ucStatOnuMpcpEntry  8  }


	ucStatOnuMpcpRegisterRequests	OBJECT-TYPE	
		SYNTAX			Counter32
		MAX-ACCESS		read-only
		STATUS			current
		DESCRIPTION		"Description."
		::=  {  ucStatOnuMpcpEntry  9  }


	ucStatOnuMpcpRegisterAcks	OBJECT-TYPE	
		SYNTAX			Counter32
		MAX-ACCESS		read-only
		STATUS			current
		DESCRIPTION		"Description."
		::=  {  ucStatOnuMpcpEntry  10  }


	ucStatOnuMpcpRegisterReports	OBJECT-TYPE	
		SYNTAX			Counter32
		MAX-ACCESS		read-only
		STATUS			current
		DESCRIPTION		"Description."
		::=  {  ucStatOnuMpcpEntry  11  }


	ucStatOnuMpcpGates	OBJECT-TYPE	
		SYNTAX			Counter32
		MAX-ACCESS		read-only
		STATUS			current
		DESCRIPTION		"Description."
		::=  {  ucStatOnuMpcpEntry  12  }


	ucStatOnuMpcpRegisters	OBJECT-TYPE	
		SYNTAX			Counter32
		MAX-ACCESS		read-only
		STATUS			current
		DESCRIPTION		"Description."
		::=  {  ucStatOnuMpcpEntry  13  }


	ucStatOnuMpcpStatMode	OBJECT-TYPE	
		SYNTAX			INTEGER  { realtime ( 1 ) , avgPerMin15 ( 2 ) , avgPerDay ( 3 ) } 
		MAX-ACCESS		read-write
		STATUS			current
		DESCRIPTION		"Description."
		::=  {  ucStatOnuMpcpEntry  14  }


	ucStatOnuMpcpReset	OBJECT-TYPE	
		SYNTAX			INTEGER  { yes ( 1 ) , no ( 2 ) } 
		MAX-ACCESS		read-write
		STATUS			current
		DESCRIPTION		"Description."
		::=  {  ucStatOnuMpcpEntry  15  }

	ucOltTxDegrade	NOTIFICATION-TYPE
		OBJECTS			{ ucAlarmOltQuaryAlarmState }
		STATUS			current
		DESCRIPTION		"Description."
		::=  {  ucOltTrap  1  }

	ucOltExternalDyingGasp	NOTIFICATION-TYPE
		OBJECTS			{ ucAlarmOltQuaryAlarmState }
		STATUS			current
		DESCRIPTION		"Description."
		::=  {  ucOltTrap  3  }

	ucOltExternalCriticalEventAlarm	NOTIFICATION-TYPE
		OBJECTS			{ ucAlarmOltQuaryAlarmState }
		STATUS			current
		DESCRIPTION		"Description."
		::=  {  ucOltTrap  4  }

	ucOltExternalAlarm	NOTIFICATION-TYPE
		OBJECTS			{ ucAlarmOltQuaryAlarmState }
		STATUS			current
		DESCRIPTION		"Description."
		::=  {  ucOltTrap  5  }

	ucOltNumberofLinksExceeded	NOTIFICATION-TYPE
		OBJECTS			{ ucAlarmOltQuaryAlarmState, ucCfgOLTNumLinks }
		STATUS			current
		DESCRIPTION		"Description."
		::=  {  ucOltTrap  6  }

	ucOltFatalOLTHwError	NOTIFICATION-TYPE
		OBJECTS			{ ucAlarmOltQuaryAlarmState }
		STATUS			current
		DESCRIPTION		"Description."
		::=  {  ucOltTrap  7  }

	ucOltMixedNetworkError	NOTIFICATION-TYPE
		OBJECTS			{ ucAlarmOltQuaryAlarmState }
		STATUS			current
		DESCRIPTION		"Description."
		::=  {  ucOltTrap  8  }

	ucOltLayer3IPMACTableOverflow	NOTIFICATION-TYPE
		OBJECTS			{ ucAlarmOltQuaryAlarmState }
		STATUS			current
		DESCRIPTION		"Description."
		::=  {  ucOltTrap  9  }

	ucOltIGMPCACforVID1	NOTIFICATION-TYPE
		OBJECTS			{ ucAlarmOltQuaryAlarmState }
		STATUS			current
		DESCRIPTION		"Description."
		::=  {  ucOltTrap  10  }

	ucOltIGMPCACforVID2	NOTIFICATION-TYPE
		OBJECTS			{ ucAlarmOltQuaryAlarmState }
		STATUS			current
		DESCRIPTION		"Description."
		::=  {  ucOltTrap  11  }

	ucOltIGMPCACforVID3	NOTIFICATION-TYPE
		OBJECTS			{ ucAlarmOltQuaryAlarmState }
		STATUS			current
		DESCRIPTION		"Description."
		::=  {  ucOltTrap  12  }

	ucOltIGMPCACforVID4	NOTIFICATION-TYPE
		OBJECTS			{ ucAlarmOltQuaryAlarmState }
		STATUS			current
		DESCRIPTION		"Description."
		::=  {  ucOltTrap  13  }

	ucOltIGMPCACforVID5	NOTIFICATION-TYPE
		OBJECTS			{ ucAlarmOltQuaryAlarmState }
		STATUS			current
		DESCRIPTION		"Description."
		::=  {  ucOltTrap  14  }

	ucOltIGMPCACforVID6	NOTIFICATION-TYPE
		OBJECTS			{ ucAlarmOltQuaryAlarmState }
		STATUS			current
		DESCRIPTION		"Description."
		::=  {  ucOltTrap  15  }

	ucOltIGMPCACforVID7	NOTIFICATION-TYPE
		OBJECTS			{ ucAlarmOltQuaryAlarmState }
		STATUS			current
		DESCRIPTION		"Description."
		::=  {  ucOltTrap  16  }

	ucOltIGMPCACforVID8	NOTIFICATION-TYPE
		OBJECTS			{ ucAlarmOltQuaryAlarmState }
		STATUS			current
		DESCRIPTION		"Description."
		::=  {  ucOltTrap  17  }

	ucOltIGMPCACforFCFS	NOTIFICATION-TYPE
		OBJECTS			{ ucAlarmOltQuaryAlarmState }
		STATUS			current
		DESCRIPTION		"Description."
		::=  {  ucOltTrap  18  }

	ucOltFPGAProgrammingFAIL	NOTIFICATION-TYPE
		OBJECTS			{ ucAlarmOltQuaryAlarmState }
		STATUS			current
		DESCRIPTION		"Description."
		::=  {  ucOltTrap  19  }

	ucOltIGMPOutOfLinearRules	NOTIFICATION-TYPE
		OBJECTS			{ ucAlarmOltQuaryAlarmState }
		STATUS			current
		DESCRIPTION		"Description."
		::=  {  ucOltTrap  20  }

	ucOltPortMACTblOverflow	NOTIFICATION-TYPE
		OBJECTS			{ ucAlarmOltPortQueryAlarmState }
		STATUS			current
		DESCRIPTION		"Description."
		::=  {  ucOltPortTrap  1  }

	ucOltPortLossofSignal	NOTIFICATION-TYPE
		OBJECTS			{ ucAlarmOltPortQueryAlarmState }
		STATUS			current
		DESCRIPTION		"Description."
		::=  {  ucOltPortTrap  2  }

	ucOltPortTxFail	NOTIFICATION-TYPE
		OBJECTS			{ ucAlarmOltPortQueryAlarmState }
		STATUS			current
		DESCRIPTION		"Description."
		::=  {  ucOltPortTrap  3  }

	ucOltPortStatisticsAlarm	NOTIFICATION-TYPE
		OBJECTS			{ ucAlarmOltPortQueryAlarmState, ucAlarmOltPortQueryStatID, ucAlarmOltPortQueryDir }
		STATUS			current
		DESCRIPTION		"Description."
		::=  {  ucOltPortTrap  4  }

	ucOltPortIGMPDOSAttack	NOTIFICATION-TYPE
		OBJECTS			{ ucAlarmOltPortQueryAlarmState }
		STATUS			current
		DESCRIPTION		"Description."
		::=  {  ucOltPortTrap  5  }

	ucOltPortDHCPARPDOSAttack	NOTIFICATION-TYPE
		OBJECTS			{ ucAlarmOltPortQueryAlarmState }
		STATUS			current
		DESCRIPTION		"Description."
		::=  {  ucOltPortTrap  6  }

	ucOltPortEAPOLDOSAttack	NOTIFICATION-TYPE
		OBJECTS			{ ucAlarmOltPortQueryAlarmState }
		STATUS			current
		DESCRIPTION		"Description."
		::=  {  ucOltPortTrap  7  }

	ucOltPortSlowProtocolLACPDOS	NOTIFICATION-TYPE
		OBJECTS			{ ucAlarmOltPortQueryAlarmState }
		STATUS			current
		DESCRIPTION		"Description."
		::=  {  ucOltPortTrap  8  }

	ucOltPortRSTPDOS	NOTIFICATION-TYPE
		OBJECTS			{ ucAlarmOltPortQueryAlarmState }
		STATUS			current
		DESCRIPTION		"Description."
		::=  {  ucOltPortTrap  9  }

	ucOltPortAutoNegFailure	NOTIFICATION-TYPE
		OBJECTS			{ ucAlarmOltPortQueryAlarmState }
		STATUS			current
		DESCRIPTION		"Description."
		::=  {  ucOltPortTrap  10  }

	ucOltLLIDMACTblOverflow	NOTIFICATION-TYPE
		OBJECTS			{ ucAlarmOltLLIDQueryAlarmState }
		STATUS			current
		DESCRIPTION		"Description."
		::=  {  ucOltLLIDTrap  1  }

	ucOltLLIDDuplicateMACRegistration	NOTIFICATION-TYPE
		OBJECTS			{ ucAlarmOltLLIDQueryAlarmState }
		STATUS			current
		DESCRIPTION		"Description."
		::=  {  ucOltLLIDTrap  2  }

	ucOltLLIDReportTimeout	NOTIFICATION-TYPE
		OBJECTS			{ ucAlarmOltLLIDQueryAlarmState }
		STATUS			current
		DESCRIPTION		"Description."
		::=  {  ucOltLLIDTrap  3  }

	ucOltLLIDStdLinkFault	NOTIFICATION-TYPE
		OBJECTS			{ ucAlarmOltLLIDQueryAlarmState }
		STATUS			current
		DESCRIPTION		"Description."
		::=  {  ucOltLLIDTrap  4  }

	ucOltLLIDOAMKeepaliveTimeout	NOTIFICATION-TYPE
		OBJECTS			{ ucAlarmOltLLIDQueryAlarmState }
		STATUS			current
		DESCRIPTION		"Description."
		::=  {  ucOltLLIDTrap  5  }

	ucOltLLIDKeyExchangeFailure	NOTIFICATION-TYPE
		OBJECTS			{ ucAlarmOltLLIDQueryAlarmState }
		STATUS			current
		DESCRIPTION		"Description."
		::=  {  ucOltLLIDTrap  6  }

	ucOltLLIDLoopback	NOTIFICATION-TYPE
		OBJECTS			{ ucAlarmOltLLIDQueryAlarmState }
		STATUS			current
		DESCRIPTION		"Description."
		::=  {  ucOltLLIDTrap  7  }

	ucOltLLIDPower	NOTIFICATION-TYPE
		OBJECTS			{ ucAlarmOltLLIDQueryAlarmState }
		STATUS			current
		DESCRIPTION		"Description."
		::=  {  ucOltLLIDTrap  9  }

	ucOltLLIDTemperature	NOTIFICATION-TYPE
		OBJECTS			{ ucAlarmOltLLIDQueryAlarmState }
		STATUS			current
		DESCRIPTION		"Description."
		::=  {  ucOltLLIDTrap  10  }

	ucOltLLIDStatisticsAlarm	NOTIFICATION-TYPE
		OBJECTS			{ ucAlarmOltLLIDQueryAlarmState, ucAlarmOltLLIDQueryStatID, ucAlarmOltLLIDQueryDir }
		STATUS			current
		DESCRIPTION		"Description."
		::=  {  ucOltLLIDTrap  11  }

	ucOltLLIDIGMPDOSAttack	NOTIFICATION-TYPE
		OBJECTS			{ ucAlarmOltLLIDQueryAlarmState }
		STATUS			current
		DESCRIPTION		"Description."
		::=  {  ucOltLLIDTrap  12  }

	ucOltLLIDDHCPARPDOSAttack	NOTIFICATION-TYPE
		OBJECTS			{ ucAlarmOltLLIDQueryAlarmState }
		STATUS			current
		DESCRIPTION		"Description."
		::=  {  ucOltLLIDTrap  13  }

	ucOltLLIDEAPOLDOSAttack	NOTIFICATION-TYPE
		OBJECTS			{ ucAlarmOltLLIDQueryAlarmState }
		STATUS			current
		DESCRIPTION		"Description."
		::=  {  ucOltLLIDTrap  14  }

	ucOltLLIDSlowProtocolLACPDOS	NOTIFICATION-TYPE
		OBJECTS			{ ucAlarmOltLLIDQueryAlarmState }
		STATUS			current
		DESCRIPTION		"Description."
		::=  {  ucOltLLIDTrap  15  }

	ucOltLLIDRSTPDOS	NOTIFICATION-TYPE
		OBJECTS			{ ucAlarmOltLLIDQueryAlarmState }
		STATUS			current
		DESCRIPTION		"Description."
		::=  {  ucOltLLIDTrap  16  }

	ucOltLLIDStdOtherAlarm	NOTIFICATION-TYPE
		OBJECTS			{ ucAlarmOltLLIDQueryAlarmState }
		STATUS			current
		DESCRIPTION		"Description."
		::=  {  ucOltLLIDTrap  17  }

	ucOnuPower	NOTIFICATION-TYPE
		OBJECTS			{ ucAlarmOnuQueryAlarmState, ucStatOnuPonIndex, ucStatOnuOnuIndex }
		STATUS			current
		DESCRIPTION		"Description."
		::=  {  ucOnuTrap  1  }

	ucOnuExternalDyingGasp	NOTIFICATION-TYPE
		OBJECTS			{ ucAlarmOnuQueryAlarmState, ucStatOnuPonIndex, ucStatOnuOnuIndex }
		STATUS			current
		DESCRIPTION		"Description."
		::=  {  ucOnuTrap  2  }

	ucOnuStandardCriticalEvent	NOTIFICATION-TYPE
		OBJECTS			{ ucAlarmOnuQueryAlarmState, ucStatOnuPonIndex, ucStatOnuOnuIndex }
		STATUS			current
		DESCRIPTION		"Description."
		::=  {  ucOnuTrap  3  }

	ucOnuExternalCriticalEventAlarm	NOTIFICATION-TYPE
		OBJECTS			{ ucAlarmOnuQueryAlarmState, ucStatOnuPonIndex, ucStatOnuOnuIndex }
		STATUS			current
		DESCRIPTION		"Description."
		::=  {  ucOnuTrap  4  }

	ucOnuTemperature	NOTIFICATION-TYPE
		OBJECTS			{ ucAlarmOnuQueryAlarmState, ucStatOnuPonIndex, ucStatOnuOnuIndex }
		STATUS			current
		DESCRIPTION		"Description."
		::=  {  ucOnuTrap  5  }

	ucOnuExternalAlarm	NOTIFICATION-TYPE
		OBJECTS			{ ucAlarmOnuQueryAlarmState, ucStatOnuPonIndex, ucStatOnuOnuIndex }
		STATUS			current
		DESCRIPTION		"Description."
		::=  {  ucOnuTrap  6  }

	ucOnuAuthenInfoUnavailable	NOTIFICATION-TYPE
		OBJECTS			{ ucAlarmOnuQueryAlarmState, ucStatOnuPonIndex, ucStatOnuOnuIndex }
		STATUS			current
		DESCRIPTION		"Description."
		::=  {  ucOnuTrap  7  }

	ucOnuPortLossofSignal	NOTIFICATION-TYPE
		OBJECTS			{ ucAlarmOnuPortQueryAlarmState, ucStatOnuPonIndex, ucStatOnuOnuIndex, ucStatOnuPortIndex }
		STATUS			current
		DESCRIPTION		"Description."
		::=  {  ucOnuPortTrap  1  }

	ucOnuPortTxFail	NOTIFICATION-TYPE
		OBJECTS			{ ucAlarmOnuPortQueryAlarmState, ucStatOnuPonIndex, ucStatOnuOnuIndex, ucStatOnuPortIndex }
		STATUS			current
		DESCRIPTION		"Description."
		::=  {  ucOnuPortTrap  2  }

	ucOnuPortMACTblOverflow	NOTIFICATION-TYPE
		OBJECTS			{ ucAlarmOnuPortQueryAlarmState, ucStatOnuPonIndex, ucStatOnuOnuIndex, ucStatOnuPortIndex }
		STATUS			current
		DESCRIPTION		"Description."
		::=  {  ucOnuPortTrap  3  }

	ucOnuPortDisabled	NOTIFICATION-TYPE
		OBJECTS			{ ucAlarmOnuPortQueryAlarmState, ucUSRPonIndex, ucUSRONUIndex, ucUSRPortIndex }
		STATUS			current
		DESCRIPTION		"Description."
		::=  {  ucOnuPortTrap  4  }

	ucOnuPortStatisticsAlarm	NOTIFICATION-TYPE
		OBJECTS			{ ucAlarmOnuPortQueryAlarmState, ucAlarmOnuPortQueryStatID, ucAlarmOnuPortQueryDir, ucStatOnuPonIndex, ucStatOnuOnuIndex, ucStatOnuPortIndex }
		STATUS			current
		DESCRIPTION		"Description."
		::=  {  ucOnuPortTrap  5  }

	ucOnuLLIDGateTimeout	NOTIFICATION-TYPE
		OBJECTS			{ ucAlarmOnuLLIDQueryAlarmState }
		STATUS			current
		DESCRIPTION		"Description."
		::=  {  ucOnuLLIDTrap  1  }

	ucOnuLLIDOAMKeepaliveTimeout	NOTIFICATION-TYPE
		OBJECTS			{ ucAlarmOnuLLIDQueryAlarmState }
		STATUS			current
		DESCRIPTION		"Description."
		::=  {  ucOnuLLIDTrap  2  }

	ucOnuLLIDKeyExchangeFailure	NOTIFICATION-TYPE
		OBJECTS			{ ucAlarmOnuLLIDQueryAlarmState }
		STATUS			current
		DESCRIPTION		"Description."
		::=  {  ucOnuLLIDTrap  3  }

	ucOnuLLIDExternalLinkFault	NOTIFICATION-TYPE
		OBJECTS			{ ucAlarmOnuLLIDQueryAlarmState }
		STATUS			current
		DESCRIPTION		"Description."
		::=  {  ucOnuLLIDTrap  4  }

	ucOnuLLIDLoopback	NOTIFICATION-TYPE
		OBJECTS			{ ucAlarmOnuLLIDQueryAlarmState }
		STATUS			current
		DESCRIPTION		"Description."
		::=  {  ucOnuLLIDTrap  5  }

	ucOnuLLIDStatisticsAlarm	NOTIFICATION-TYPE
		OBJECTS			{ ucAlarmOnuLLIDQueryAlarmState, ucAlarmOnuLLIDQueryStatID, ucAlarmOnuLLIDQueryDir }
		STATUS			current
		DESCRIPTION		"Description."
		::=  {  ucOnuLLIDTrap  6  }

	ucOnuLLIDStandardDyingGasp	NOTIFICATION-TYPE
		OBJECTS			{ ucAlarmOltLLIDQueryAlarmState }
		STATUS			current
		DESCRIPTION		"Description."
		::=  {  ucOnuLLIDTrap  7  }

	ucOnuLLIDLinkDiscovery	NOTIFICATION-TYPE
		OBJECTS			{ ucAlarmOltLLIDQueryAlarmState }
		STATUS			current
		DESCRIPTION		"Description."
		::=  {  ucOnuLLIDTrap  8  }

	ucOltCmdNotSupport	NOTIFICATION-TYPE
		OBJECTS			{ ucAlarmOltQuaryAlarmState }
		STATUS			current
		DESCRIPTION		"Description."
		::=  {  ucOltCmdTrap  1  }

	ucOltCmdIdunKnown	NOTIFICATION-TYPE
		OBJECTS			{ ucAlarmOltQuaryAlarmState }
		STATUS			current
		DESCRIPTION		"Description."
		::=  {  ucOltCmdTrap  2  }

	ucOltCmdParameterOutOfRange	NOTIFICATION-TYPE
		OBJECTS			{ ucAlarmOltQuaryAlarmState }
		STATUS			current
		DESCRIPTION		"Description."
		::=  {  ucOltCmdTrap  3  }

	ucOltCmdCommandfailed	NOTIFICATION-TYPE
		OBJECTS			{ ucAlarmOltQuaryAlarmState }
		STATUS			current
		DESCRIPTION		"Description."
		::=  {  ucOltCmdTrap  4  }

	ucOltCmdNotenoughresources	NOTIFICATION-TYPE
		OBJECTS			{ ucAlarmOltQuaryAlarmState }
		STATUS			current
		DESCRIPTION		"Description."
		::=  {  ucOltCmdTrap  5  }

	ucOltCmdNotapplicable	NOTIFICATION-TYPE
		OBJECTS			{ ucAlarmOltQuaryAlarmState }
		STATUS			current
		DESCRIPTION		"Description."
		::=  {  ucOltCmdTrap  6  }

	ucOltCmdUnknownerror	NOTIFICATION-TYPE
		OBJECTS			{ ucAlarmOltQuaryAlarmState }
		STATUS			current
		DESCRIPTION		"Description."
		::=  {  ucOltCmdTrap  7  }

	ucOltCmdCommandtooshort	NOTIFICATION-TYPE
		OBJECTS			{ ucAlarmOltQuaryAlarmState }
		STATUS			current
		DESCRIPTION		"Description."
		::=  {  ucOltCmdTrap  8  }

	ucOltCmdMoretocome	NOTIFICATION-TYPE
		OBJECTS			{ ucAlarmOltQuaryAlarmState }
		STATUS			current
		DESCRIPTION		"Description."
		::=  {  ucOltCmdTrap  9  }

	ucOltCmdNoOAMBandwidth	NOTIFICATION-TYPE
		OBJECTS			{ ucAlarmOltQuaryAlarmState }
		STATUS			current
		DESCRIPTION		"Description."
		::=  {  ucOltCmdTrap  10  }

	ucOltCmdNoONUResponse	NOTIFICATION-TYPE
		OBJECTS			{ ucAlarmOltQuaryAlarmState }
		STATUS			current
		DESCRIPTION		"Description."
		::=  {  ucOltCmdTrap  11  }

	ucOltCmdWrongMode	NOTIFICATION-TYPE
		OBJECTS			{ ucAlarmOltQuaryAlarmState }
		STATUS			current
		DESCRIPTION		"Description."
		::=  {  ucOltCmdTrap  12  }

	ucOltCmdONUReturnedError	NOTIFICATION-TYPE
		OBJECTS			{ ucAlarmOltQuaryAlarmState }
		STATUS			current
		DESCRIPTION		"Description."
		::=  {  ucOltCmdTrap  13  }







    -- 2.6.12
	ucCTC OBJECT IDENTIFIER ::= { ucPon 12 }  -- Now add this branch !!! 
	
	              
	-- 2.6.12.1   
	-- ***************************** ONU MESSAGES *****************************
	ucOnuMsg OBJECT IDENTIFIER ::= { ucCTC 1 }      
        
-- Table with ONU index
    	-- 2.6.12.1.1
    	ucOnuMsgOnuTable OBJECT-TYPE
    		SYNTAX SEQUENCE OF UcOnuMsgOnuEntry
    		MAX-ACCESS not-accessible
    		STATUS mandatory
    		DESCRIPTION "" 
    	::= { ucOnuMsg 1 }
    	
    	-- 2.6.12.1.1.1
    	ucOnuMsgOnuEntry OBJECT-TYPE    
    		SYNTAX UcOnuMsgOnuEntry
    		MAX-ACCESS not-accessible
    		STATUS mandatory
    		DESCRIPTION ""
    		INDEX { ucOnuMsgOnuSlotIndex,ucOnuMsgOnuPonIndex,ucOnuMsgOnuIndex }
    	::= { ucOnuMsgOnuTable 1 }
    	
    	UcOnuMsgOnuEntry ::= SEQUENCE
    	{      
    		ucOnuMsgOnuSlotIndex	Integer32,
    		ucOnuMsgOnuPonIndex		Integer32,
    		ucOnuMsgOnuIndex		Integer32,
    	    ucOnuMsgOnuReset        Integer32,
    	    ucOnuMsgOnuDba          OCTET STRING, -- 18
    	    ucOnuMsgOnuInfo         OCTET STRING, -- 38
    	    ucOnuMsgOnuFec          Integer32,
    	    ucOnuMsgOnuFecAbility   Integer32
    	}
    	   
   		-- 2.6.12.1.1.1.1
   		ucOnuMsgOnuSlotIndex OBJECT-TYPE
   	 		SYNTAX  Integer32 (1..16)
     		MAX-ACCESS  read-only
     		STATUS current
     		DESCRIPTION ""
   		::= { ucOnuMsgOnuEntry 1 }
   		
   		-- 2.6.12.1.1.1.2
   		ucOnuMsgOnuPonIndex OBJECT-TYPE
   	 		SYNTAX  Integer32 (1..32)
     		MAX-ACCESS  read-only
     		STATUS current
     		DESCRIPTION ""
   		::= { ucOnuMsgOnuEntry 2 }   
       	   
   		-- 2.6.12.1.1.1.3
   		ucOnuMsgOnuIndex OBJECT-TYPE
   	 		SYNTAX  Integer32 (1..256)
     		MAX-ACCESS  read-only
     		STATUS current
     		DESCRIPTION ""
   		::= { ucOnuMsgOnuEntry 3 }

   		-- 2.6.12.1.1.1.4
   		ucOnuMsgOnuReset OBJECT-TYPE
   	 		SYNTAX  Integer32 {
   	 			none(0),
   	 			reset(1)
   	 		}
     		MAX-ACCESS  read-write
     		STATUS current
     		DESCRIPTION "CTC reset Onu"
   		::= { ucOnuMsgOnuEntry 4 }
   		   		   		                        
   		-- 2.6.12.1.1.1.5
   		ucOnuMsgOnuDba OBJECT-TYPE
   	 		SYNTAX  OCTET STRING (SIZE(0..18))
     		MAX-ACCESS  read-write
     		STATUS current
     		DESCRIPTION
     		"Length ---- Info -------------------------------------------
     		 1           Number of queue sets, Number of times the following fields repeat
     		      ############################################################################################
     		      1      Bitmap of which the following 8 values are to be used. Low order bit of this byte 
     		             corresponds to first array element. Note that all of the following thresholds are 
     		             always included in the host interface message, regardless of what the bitmap is set to.
     		      2      Threshold 0
     		      2      Threshold 1
     		      2      Threshold 2
     		      2      Threshold 3
     		      2      Threshold 4
     		      2      Threshold 5
     		      2      Threshold 6
     		      2      Threshold 7"    		 
     	::= { ucOnuMsgOnuEntry 5 }   		                          
   		   
   		-- 2.6.12.1.1.1.6
   		ucOnuMsgOnuInfo OBJECT-TYPE
   	 		SYNTAX  OCTET STRING (SIZE(0..38))
     		MAX-ACCESS  read-write
     		STATUS current
     		DESCRIPTION
     		"Length ---- Info -------------------------------------------
     		 3           CTC OUI,  Identifies this TLV
     		 2           Length of data following this: 33,Allows the host to easily skip irrelevant information TLVs
     		 1           Extensions version,Version of CTC extensions currently in use for this link
     		 10          Data contents of CTC Get ONU Capabilities, Link label not included
     		 2           Data contents of CTC Get ONU Firmware Version, Link label not included
     		 8           Data contents of CTC Get ONU Chip Info, Link label not included
     		 12          Data contents of CTC Get ONU Serial Number, Link label not included"     		 	   		
     	::= { ucOnuMsgOnuEntry 6 }
     	                 
   		-- 2.6.12.1.1.1.7
   		ucOnuMsgOnuFec OBJECT-TYPE
   	 		SYNTAX  Integer32 {
   	 			unknow(1),
   	 			enable(2),
   	 			disable(3)
   	 		}
     		MAX-ACCESS  read-write
     		STATUS current
     		DESCRIPTION "" 		
   		::= { ucOnuMsgOnuEntry 7 }

   		-- 2.6.12.1.1.1.8
   		ucOnuMsgOnuFecAbility OBJECT-TYPE
   	 		SYNTAX  Integer32 {
   	 			unknow(1),
   	 			enable(2),
   	 			disable(3)
   	 		}
   	 		MAX-ACCESS  read-only
     		STATUS current
     		DESCRIPTION ""
   		::= { ucOnuMsgOnuEntry 8 }
     	                 
     	   		   
   		
-- Table with ONU LINK index 
    	-- 2.6.12.1.2
    	ucOnuMsgLLIDTable OBJECT-TYPE
    		SYNTAX SEQUENCE OF UcOnuMsgLLIDEntry
    		MAX-ACCESS not-accessible
    		STATUS mandatory
    		DESCRIPTION "" 
    	::= { ucOnuMsg 2 }
    	
    	-- 2.6.12.1.2.1
    	ucOnuMsgLLIDEntry OBJECT-TYPE    
    		SYNTAX UcOnuMsgLLIDEntry
    		MAX-ACCESS not-accessible
    		STATUS mandatory
    		DESCRIPTION ""
    		INDEX { ucOnuMsgLLIDSlotIndex,ucOnuMsgLLIDPonIndex,ucOnuMsgLLIDOnuIndex,ucOnuMsgLLIDIndex }
    	::= { ucOnuMsgLLIDTable 1 }
    	
    	UcOnuMsgLLIDEntry ::= SEQUENCE
    	{      
    		ucOnuMsgLLIDSlotIndex	Integer32,
    		ucOnuMsgLLIDPonIndex	Integer32,
    		ucOnuMsgLLIDOnuIndex	Integer32,
    	    ucOnuMsgLLIDIndex		Integer32,
    	    ucOnuMsgLLIDCapability  OCTET STRING, -- 26
    	    ucOnuMsgLLIDFirmVer     OCTET STRING, -- ~256
    	    ucOnuMsgLLIDChipInfo    OCTET STRING, -- 8
    	    ucOnuMsgLLIDSerialNum   OCTET STRING  -- 40
    	}
    	   
   		-- 2.6.12.1.2.1.1
   		ucOnuMsgLLIDSlotIndex OBJECT-TYPE
   	 		SYNTAX  Integer32 (1..16)
     		MAX-ACCESS  read-only
     		STATUS current
     		DESCRIPTION ""
   		::= { ucOnuMsgLLIDEntry 1 }
   		
   		-- 2.6.12.1.2.1.2
   		ucOnuMsgLLIDPonIndex OBJECT-TYPE
   	 		SYNTAX  Integer32 (1..32)
     		MAX-ACCESS  read-only
     		STATUS current
     		DESCRIPTION ""
   		::= { ucOnuMsgLLIDEntry 2 }   
       	   
   		-- 2.6.12.1.2.1.3
   		ucOnuMsgLLIDOnuIndex OBJECT-TYPE
   	 		SYNTAX  Integer32 (1..256)
     		MAX-ACCESS  read-only
     		STATUS current
     		DESCRIPTION ""
   		::= { ucOnuMsgLLIDEntry 3 }
   		
   		-- 2.6.12.1.2.1.4
   		ucOnuMsgLLIDIndex OBJECT-TYPE
   	 		SYNTAX  Integer32 (1..4096)
     		MAX-ACCESS  read-only
     		STATUS current
     		DESCRIPTION ""
   		::= { ucOnuMsgLLIDEntry 4 }
   		               
   		-- 2.6.12.1.2.1.5
   		ucOnuMsgLLIDCapability OBJECT-TYPE
   	 		SYNTAX  OCTET STRING (SIZE(0..26))
     		MAX-ACCESS  read-only
     		STATUS current
     		DESCRIPTION 
     		"Length ---- Info -------------------------------------------
             1           Services Supported,
                         Bit 0: GE port Yes/No
                         Bit 1: FE port Yes/No
                         Bit 2: VOIP support Yes/No
                         Bit 3: TDM support Yes/No
             1           Number of GE ports
             8           GE port bitmap      Bitmap of ports supporting GE
             1           Number of FE ports
             8           FE port bitmap      Bitmap of ports supporting FE
             1           Number of POTS ports
             1           Number of E1 ports 
             1           Number of upstream queues
             1           Maximum queues per port, upstream
             1           Number of downstream queues
             1           Maximum queues per port, downstream
             1           Battery backup      (1)Exists (0)Does not exist"
   		::= { ucOnuMsgLLIDEntry 5 }   		               

   		-- 2.6.12.1.2.1.6
   		ucOnuMsgLLIDFirmVer OBJECT-TYPE
   	 		SYNTAX  OCTET STRING (SIZE(0..256))
     		MAX-ACCESS  read-only
     		STATUS current
     		DESCRIPTION
     		"Length ---- Info -------------------------------------------
     		 1           Len      Length of bytes to follow
     		 (Len)                Length of bytes of firmware version"     		
     	::= { ucOnuMsgLLIDEntry 6 } 
     		
   		-- 2.6.12.1.2.1.7
   		ucOnuMsgLLIDChipInfo OBJECT-TYPE
   	 		SYNTAX  OCTET STRING (SIZE(0..8))
     		MAX-ACCESS  read-only
     		STATUS current
     		DESCRIPTION
     		"Length ---- Info -------------------------------------------
     		 2           Vendor ID, JDEC ID for ONU vendor
     		 2           Chipset ID, Chipset part number
     		 1           Revision, Chip revision
     		 3           Date, YY/MM/DD"     		 	
     	::= { ucOnuMsgLLIDEntry 7 }
     	
   		-- 2.6.12.1.2.1.8
   		ucOnuMsgLLIDSerialNum OBJECT-TYPE
   	 		SYNTAX  OCTET STRING (SIZE(0..40))
     		MAX-ACCESS  read-only
     		STATUS current
     		DESCRIPTION
     		"Length ---- Info -------------------------------------------
     		 4           Vendor ID
     		 4           ONU Model
     		 6           ONU MAC address
     		 8           Hardware Version   ASCII
     		 16          Software Version   ASCII"	   		
     	::= { ucOnuMsgLLIDEntry 8 }
     	
     	     	     		
     		
-- Table with OLT PORT index (OLT PON PORT)
    	-- 2.6.12.1.3
    	ucOnuMsgOltPortTable OBJECT-TYPE
    		SYNTAX SEQUENCE OF UcOnuMsgOltPortEntry
    		MAX-ACCESS not-accessible
    		STATUS mandatory
    		DESCRIPTION "OLT PON PORT TABLE" 
    	::= { ucOnuMsg 3 }
    	
    	-- 2.6.12.1.3.1
    	ucOnuMsgOltPortEntry OBJECT-TYPE    
    		SYNTAX UcOnuMsgOltPortEntry
    		MAX-ACCESS not-accessible
    		STATUS mandatory
    		DESCRIPTION ""
    		INDEX { ucOnuMsgOltPortSlotIndex,ucOnuMsgOltPortIndex }
    	::= { ucOnuMsgOltPortTable 1 }
    	
    	UcOnuMsgOltPortEntry ::= SEQUENCE
    	{      
    		ucOnuMsgOltPortSlotIndex	Integer32,
    		ucOnuMsgOltPortIndex		Integer32,
    		ucOnuMsgOltPortGetAllowLinks   OCTET STRING, -- 6*N
    		ucOnuMsgOltPortClearAllowLinks Integer32,
    		ucOnuMsgOltPortAddAllowLinks   OCTET STRING, -- 6*N
    		ucOnuMsgOltPortDelAllowLinks   OCTET STRING  -- 6*N    	
    	}
    	   
   		-- 2.6.12.1.3.1.1
   		ucOnuMsgOltPortSlotIndex OBJECT-TYPE
   	 		SYNTAX  Integer32 (1..16)
     		MAX-ACCESS  read-only
     		STATUS current
     		DESCRIPTION ""
   		::= { ucOnuMsgOltPortEntry 1 }
   		
   		-- 2.6.12.1.3.1.2
   		ucOnuMsgOltPortIndex OBJECT-TYPE
   	 		SYNTAX  Integer32 (1..16)
     		MAX-ACCESS  read-only
     		STATUS current
     		DESCRIPTION ""
   		::= { ucOnuMsgOltPortEntry 2 }   		
   		   	
   		-- 2.6.12.1.3.1.3
   		ucOnuMsgOltPortGetAllowLinks OBJECT-TYPE
   	 		SYNTAX  OCTET STRING (SIZE(0..1024))
     		MAX-ACCESS  read-write
     		STATUS current
     		DESCRIPTION 
     		"Length ---- Mean ----------- Info -----------------
     		 6*N         List of MAC addresses currently in the Allowed list"
   		::= { ucOnuMsgOltPortEntry 3 }
   		
   		-- 2.6.12.1.3.1.4
   		ucOnuMsgOltPortClearAllowLinks OBJECT-TYPE
   	 		SYNTAX  Integer32 {
   	 			none(0),
   	 			clear(1)
   	 		}   	 		
     		MAX-ACCESS  read-write
     		STATUS current
     		DESCRIPTION ""
   		::= { ucOnuMsgOltPortEntry 4 }    		
   		   	
   		-- 2.6.12.1.3.1.5
   		ucOnuMsgOltPortAddAllowLinks OBJECT-TYPE
   	 		SYNTAX  OCTET STRING (SIZE(0..1024))
     		MAX-ACCESS  read-write
     		STATUS current
     		DESCRIPTION 
     		"Length ---- Mean ----------- Info -----------------
     		 6*N         List of MAC addresses to add to Allowed list"
   		::= { ucOnuMsgOltPortEntry 5 }
   		   	
   		-- 2.6.12.1.3.1.6
   		ucOnuMsgOltPortDelAllowLinks OBJECT-TYPE
   	 		SYNTAX  OCTET STRING (SIZE(0..1024))
     		MAX-ACCESS  read-write
     		STATUS current
     		DESCRIPTION 
     		"Length ---- Mean ----------- Info -----------------
     		 6*N         List of MAC addresses to remove from Allowed list"
   		::= { ucOnuMsgOltPortEntry 6 }   		
   		   		
   		   		   		   		
   		   		   		

-- Table with OLT index
    	-- 2.6.12.1.4
    	ucOnuMsgOltTable OBJECT-TYPE
    		SYNTAX SEQUENCE OF UcOnuMsgOltEntry
    		MAX-ACCESS not-accessible
    		STATUS mandatory
    		DESCRIPTION "" 
    	::= { ucOnuMsg 4 }
    	
    	-- 2.6.12.1.4.1
    	ucOnuMsgOltEntry OBJECT-TYPE    
    		SYNTAX UcOnuMsgOltEntry
    		MAX-ACCESS not-accessible
    		STATUS mandatory
    		DESCRIPTION ""
    		INDEX { ucOnuMsgOltSlotIndex }
    	::= { ucOnuMsgOltTable 1 }
    	
    	UcOnuMsgOltEntry ::= SEQUENCE
    	{      
    		ucOnuMsgOltSlotIndex	Integer32,
    		ucOnuMsgOltCtcConfig    OCTET STRING  -- 4    	
    	}
    	   
   		-- 2.6.12.1.4.1.1
   		ucOnuMsgOltSlotIndex OBJECT-TYPE
   	 		SYNTAX  Integer32 (1..16)
     		MAX-ACCESS  read-only
     		STATUS current
     		DESCRIPTION ""
   		::= { ucOnuMsgOltEntry 1 }
   		
   		-- 2.6.12.1.4.1.2
   		ucOnuMsgOltCtcConfig OBJECT-TYPE
   	 		SYNTAX  OCTET STRING (SIZE(0..4))
     		MAX-ACCESS  read-write
     		STATUS current
     		DESCRIPTION 
     		"Length ---- Mean ----------- Info -----------------
     		 1           state            (0)disable (1)enable
     		 3           CTC OUI          The OUI to use when negotiating CTC extensions with links
     		 1           Reserved         Set to 0"
   		::= { ucOnuMsgOltEntry 2 } 
   		
   		   		   		   		   		   
   
	-- 2.6.12.2  
	-- ***************************** PORT MESSAGES *****************************
	ucPortMsg OBJECT IDENTIFIER ::= { ucCTC 2 }
	          
-- Table with OLT PORT index
    	-- 2.6.12.2.1
    	ucPortMsgOltPortTable OBJECT-TYPE
    		SYNTAX SEQUENCE OF UcPortMsgOltPortEntry
    		MAX-ACCESS not-accessible
    		STATUS mandatory
    		DESCRIPTION "" 
    	::= { ucPortMsg 1 }
    	
    	-- 2.6.12.2.1.1
    	ucPortMsgOltPortEntry OBJECT-TYPE    
    		SYNTAX UcPortMsgOltPortEntry
    		MAX-ACCESS not-accessible
    		STATUS mandatory
    		DESCRIPTION ""
    		INDEX { ucPortMsgOltPortSlotIndex,ucPortMsgOltPortIndex }
    	::= { ucPortMsgOltPortTable 1 }
    	
    	UcPortMsgOltPortEntry ::= SEQUENCE
    	{      
    		ucPortMsgOltPortSlotIndex	Integer32,
    		ucPortMsgOltPortIndex		Integer32,
    		ucPortMsgOltPortEnable             Integer32,
    		ucPortMsgOltPortPolicing    	   OCTET STRING, -- 10
    		ucPortMsgOltPortGet         	   Integer32,
    		ucPortMsgOltPortSetEthPort         OCTET STRING, -- 4
    		ucPortMsgOltPortGetEthPortState    OCTET STRING, -- 6+2n+2n
    		ucPortMsgOltPortDnStreamRateLimit  OCTET STRING  -- 7  	
    	}
    	   
   		-- 2.6.12.2.1.1.1
   		ucPortMsgOltPortSlotIndex OBJECT-TYPE
   	 		SYNTAX  Integer32 (1..16)
     		MAX-ACCESS  read-only
     		STATUS current
     		DESCRIPTION ""
   		::= { ucPortMsgOltPortEntry 1 }
   		
   		-- 2.6.12.2.1.1.2
   		ucPortMsgOltPortIndex OBJECT-TYPE
   	 		SYNTAX  Integer32 (1..16)
     		MAX-ACCESS  read-only
     		STATUS current
     		DESCRIPTION ""
   		::= { ucPortMsgOltPortEntry 2 }
   		
   		-- 2.6.12.2.1.1.3
   		ucPortMsgOltPortEnable OBJECT-TYPE
   	 		SYNTAX  Integer32 {
   	 			disable(0),
   	 			enable(1)
   	 		}
     		MAX-ACCESS  read-write
     		STATUS current
     		DESCRIPTION ""
   		::= { ucPortMsgOltPortEntry 3 }
   		
   		-- 2.6.12.2.1.1.4
   		ucPortMsgOltPortPolicing OBJECT-TYPE
   	 		SYNTAX  OCTET STRING (SIZE(0..10))
     		MAX-ACCESS  read-write
     		STATUS current
     		DESCRIPTION 
     		"Length ---- Mean ----------- Info -----------------
     		 1           Port policing state, 0 = disabled, 1= enabled
     		 3           Port policing CIR,This parameter identifies the committed information rate of the port in Kbps
     		 3           Port policing bucket,This parameter identifies the depth of this token bucket to be tolerant 
     		             of a certain burst size
     		 3           Port policing extra burst size, This parameter identifies an extra token to permit the 
     		             forwarding engine to finish the packet being sent when the CBS is exhausted"  		 
   		::= { ucPortMsgOltPortEntry 4 }   		
   		
   		-- 2.6.12.2.1.1.5
   		ucPortMsgOltPortGet OBJECT-TYPE
   	 		SYNTAX  Integer32 {
   	 			disable(0),
   	 			enable(1)
   	 		}
     		MAX-ACCESS  read-only
     		STATUS current
     		DESCRIPTION ""
   		::= { ucPortMsgOltPortEntry 5 }
   		
   		-- 2.6.12.2.1.1.6
   		ucPortMsgOltPortSetEthPort OBJECT-TYPE
   	 		SYNTAX  OCTET STRING (SIZE(0..4))
     		MAX-ACCESS  read-write
     		STATUS current
     		DESCRIPTION 
     		"Length ---- Mean ----------- Info -----------------
     		 1           Flow control,  0 = disabled, 1= enabled
     		 1           ActAutoAdminControl, 0 = disabled, 1 = enabled
     		 1           ActAutoRenegotiate,  0 = do not restart, 1 = restart auto negotiation
     		 1           ActPhyAdminControl,  0 = disabled, 1 =enabled"	 
   		::= { ucPortMsgOltPortEntry 6 }
   		
   		-- 2.6.12.2.1.1.7
   		ucPortMsgOltPortGetEthPortState OBJECT-TYPE
   	 		SYNTAX  OCTET STRING (SIZE(0..256))
     		MAX-ACCESS  read-write
     		STATUS current
     		DESCRIPTION 
     		"Length ---- Mean ----------- Info -----------------
     		 1           Link UP/DOWN     1 = linked, 0 = not linked
     		 1           Flow control     0 = disabled, 1 = enabled
     		 1           aPhyAdminState   0 = disabled, 1 = enabled
     		 1           aAutoNegAdminState   0 = disabled, 1 = enabled 
     		 
     		 1     Number of local abilities to follow, n 
     		       ---------------------------------------------
     		       2*n   aAutoNegLocalTechnologyAbility, see below Value Table
     		       
     		 1     Number of advertised abilities to follow, n
     		       ---------------------------------------------     		 	   
     		       2*n   aAutoNegAdvertisedTechnologyAbility, see below Value Table 
     		             
     		 ======================================================================
     		 Value Table:
     		 OamAutoCapGlobal                 0
     		 OamAutoCapOthe                   1
     		 OamAutoCapUnknown                2
     		 OamAutoCap10T                    14
     		 OamAutoCap10TFD                  142
     		 OamAutoCap100T4                  23
     		 OamAutoCap100TX                  25
     		 OamAutoCap100TXFD                252
     		 OamAutoCapFdxPause               312
     		 OamAutoCapFdxAPause              313
     		 OamAutoCapFdxSPause              314
     		 OamAutoCapFdxBPause              315
     		 OamAutoCap100T2                  32
     		 OamAutoCap100T2FD                322
     		 OamAutoCap1000X                  36
     		 OamAutoCap1000XFD                362
     		 OamAutoCap1000T                  40
     		 OamAutoCap1000TFD                402
     		 OamAutoCapRemFault1              37
     		 OamAutoCapRemFault2              372
     		 OamAutoCapIsoEthernet            8029"		  		 
   		::= { ucPortMsgOltPortEntry 7 }   		   		   		   		
   		        
   		-- 2.6.12.2.1.1.8
   		ucPortMsgOltPortDnStreamRateLimit OBJECT-TYPE
   	 		SYNTAX  OCTET STRING (SIZE(0..7))
     		MAX-ACCESS  read-write
     		STATUS current
     		DESCRIPTION 
     		"Length ---- Mean ----------- Info -----------------
     		 1           Port DS rate limiting state, 0 = disabled, 1= enabled
     		 3           Port DS rate limiting CIR, This parameter identifies the downstream Committed Information Rate of the port in Kbps
     		 3           Port DS rate limiting PIR, This parameter identifies the downstream Peak Information Rate in Kbps"	 
   		::= { ucPortMsgOltPortEntry 8 } 
   		
   		
   		   		        
   		
   		
-- Table with ONU PORT index
    	-- 2.6.12.2.2
    	ucPortMsgOnuPortTable OBJECT-TYPE
    		SYNTAX SEQUENCE OF UcPortMsgOnuPortEntry
    		MAX-ACCESS not-accessible
    		STATUS mandatory
    		DESCRIPTION "" 
    	::= { ucPortMsg 2 }
    	
    	-- 2.6.12.2.2.1
    	ucPortMsgOnuPortEntry OBJECT-TYPE    
    		SYNTAX UcPortMsgOnuPortEntry
    		MAX-ACCESS not-accessible
    		STATUS mandatory
    		DESCRIPTION ""
    		INDEX { ucPortMsgOnuPortSlotIndex,ucPortMsgOnuPortPonIndex,ucPortMsgOnuPortOnuIndex,ucPortMsgOnuPortIndex }
    	::= { ucPortMsgOnuPortTable 1 }
    	
    	UcPortMsgOnuPortEntry ::= SEQUENCE
    	{      
    		ucPortMsgOnuPortSlotIndex	Integer32,
    		ucPortMsgOnuPortPonIndex	Integer32,   
    		ucPortMsgOnuPortOnuIndex    Integer32,
    		ucPortMsgOnuPortIndex		Integer32,
    		ucPortMsgOnuPortEnable             Integer32,
    		ucPortMsgOnuPortPolicing    	   OCTET STRING, -- 10
    		ucPortMsgOnuPortGet         	   Integer32,
    		ucPortMsgOnuPortSetEthPort         OCTET STRING, -- 4
    		ucPortMsgOnuPortGetEthPortState    OCTET STRING, -- 6+2n+2n
    		ucPortMsgOnuPortDnStreamRateLimit  OCTET STRING  -- 7    	
    	}
    	   
   		-- 2.6.12.2.2.1.1
   		ucPortMsgOnuPortSlotIndex OBJECT-TYPE
   	 		SYNTAX  Integer32 (1..16)
     		MAX-ACCESS  read-only
     		STATUS current
     		DESCRIPTION ""
   		::= { ucPortMsgOnuPortEntry 1 }
   		
   		-- 2.6.12.2.2.1.2
   		ucPortMsgOnuPortPonIndex OBJECT-TYPE
   	 		SYNTAX  Integer32 (1..32)
     		MAX-ACCESS  read-only
     		STATUS current
     		DESCRIPTION ""
   		::= { ucPortMsgOnuPortEntry 2 }   
       	   
   		-- 2.6.12.2.2.1.3
   		ucPortMsgOnuPortOnuIndex OBJECT-TYPE
   	 		SYNTAX  Integer32 (1..256)
     		MAX-ACCESS  read-only
     		STATUS current
     		DESCRIPTION ""
   		::= { ucPortMsgOnuPortEntry 3 }
   		       
   		-- 2.6.12.2.2.1.4
   		ucPortMsgOnuPortIndex OBJECT-TYPE
   	 		SYNTAX  Integer32 (1..16)
     		MAX-ACCESS  read-only
     		STATUS current
     		DESCRIPTION ""
   		::= { ucPortMsgOnuPortEntry 4 }   		       
   		
   		-- 2.6.12.2.2.1.5
   		ucPortMsgOnuPortEnable OBJECT-TYPE
   	 		SYNTAX  Integer32 {
   	 			disable(0),
   	 			enable(1)
   	 		}
     		MAX-ACCESS  read-write
     		STATUS current
     		DESCRIPTION ""
   		::= { ucPortMsgOnuPortEntry 5 }
   		
   		-- 2.6.12.2.2.1.6
   		ucPortMsgOnuPortPolicing OBJECT-TYPE
   	 		SYNTAX  OCTET STRING (SIZE(0..10))
     		MAX-ACCESS  read-write
     		STATUS current
     		DESCRIPTION 
     		"Length ---- Mean ----------- Info -----------------
     		 1           Port policing state, 0 = disabled, 1= enabled
     		 3           Port policing CIR,This parameter identifies the committed information rate of the port in Kbps
     		 3           Port policing bucket,This parameter identifies the depth of this token bucket to be tolerant 
     		             of a certain burst size
     		 3           Port policing extra burst size, This parameter identifies an extra token to permit the 
     		             forwarding engine to finish the packet being sent when the CBS is exhausted"  		 
   		::= { ucPortMsgOnuPortEntry 6 }   		
   		
   		-- 2.6.12.2.2.1.7
   		ucPortMsgOnuPortGet OBJECT-TYPE
   	 		SYNTAX  Integer32 {
   	 			disable(0),
   	 			enable(1)
   	 		}
     		MAX-ACCESS  read-only
     		STATUS current
     		DESCRIPTION ""
   		::= { ucPortMsgOnuPortEntry 7 }
   		
   		-- 2.6.12.2.2.1.8
   		ucPortMsgOnuPortSetEthPort OBJECT-TYPE
   	 		SYNTAX  OCTET STRING (SIZE(0..4))
     		MAX-ACCESS  read-write
     		STATUS current
     		DESCRIPTION 
     		"Length ---- Mean ----------- Info -----------------
     		 1           Flow control,  0 = disabled, 1= enabled
     		 1           ActAutoAdminControl, 0 = disabled, 1 = enabled
     		 1           ActAutoRenegotiate,  0 = do not restart, 1 = restart auto negotiation
     		 1           ActPhyAdminControl,  0 = disabled, 1 =enabled"	 
   		::= { ucPortMsgOnuPortEntry 8 }
   		
   		-- 2.6.12.2.2.1.9
   		ucPortMsgOnuPortGetEthPortState OBJECT-TYPE
   	 		SYNTAX  OCTET STRING (SIZE(0..256))
     		MAX-ACCESS  read-write
     		STATUS current
     		DESCRIPTION 
     		"Length ---- Mean ----------- Info -----------------
     		 1           Link UP/DOWN     1 = linked, 0 = not linked
     		 1           Flow control     0 = disabled, 1 = enabled
     		 1           aPhyAdminState   0 = disabled, 1 = enabled
     		 1           aAutoNegAdminState   0 = disabled, 1 = enabled 
     		 
     		 1     Number of local abilities to follow, n 
     		       ---------------------------------------------
     		       2*n   aAutoNegLocalTechnologyAbility, see below Value Table
     		       
     		 1     Number of advertised abilities to follow, n  
     		       ---------------------------------------------
     		       2*n   aAutoNegAdvertisedTechnologyAbility, see below Value Table
     		        
     		 ======================================================================     		            		
     		 Value Table:
     		 OamAutoCapGlobal                 0
     		 OamAutoCapOthe                   1
     		 OamAutoCapUnknown                2
     		 OamAutoCap10T                    14
     		 OamAutoCap10TFD                  142
     		 OamAutoCap100T4                  23
     		 OamAutoCap100TX                  25
     		 OamAutoCap100TXFD                252
     		 OamAutoCapFdxPause               312
     		 OamAutoCapFdxAPause              313
     		 OamAutoCapFdxSPause              314
     		 OamAutoCapFdxBPause              315
     		 OamAutoCap100T2                  32
     		 OamAutoCap100T2FD                322
     		 OamAutoCap1000X                  36
     		 OamAutoCap1000XFD                362
     		 OamAutoCap1000T                  40
     		 OamAutoCap1000TFD                402
     		 OamAutoCapRemFault1              37
     		 OamAutoCapRemFault2              372
     		 OamAutoCapIsoEthernet            8029"		  		 
   		::= { ucPortMsgOnuPortEntry 9 }   		   		   		   		
   		        
   		-- 2.6.12.2.2.1.10
   		ucPortMsgOnuPortDnStreamRateLimit OBJECT-TYPE
   	 		SYNTAX  OCTET STRING (SIZE(0..7))
     		MAX-ACCESS  read-write
     		STATUS current
     		DESCRIPTION 
     		"Length ---- Mean ----------- Info -----------------
     		 1           Port DS rate limiting state, 0 = disabled, 1= enabled
     		 3           Port DS rate limiting CIR, This parameter identifies the downstream Committed Information Rate of the port in Kbps
     		 3           Port DS rate limiting PIR, This parameter identifies the downstream Peak Information Rate in Kbps"	 
   		::= { ucPortMsgOnuPortEntry 10 }
   		
   		
   		   		
   		   		
   		
   			          
	-- 2.6.12.3    
	-- ***************************** VLAN MESSAGES *****************************
	ucVlanMsg OBJECT IDENTIFIER ::= { ucCTC 3 }                         		
   		
-- Table with ONU PORT index
    	-- 2.6.12.3.1
    	ucVlanMsgOnuPortTable OBJECT-TYPE
    		SYNTAX SEQUENCE OF UcVlanMsgOnuPortEntry
    		MAX-ACCESS not-accessible
    		STATUS mandatory
    		DESCRIPTION "" 
    	::= { ucVlanMsg 1 }
    	
    	-- 2.6.12.3.1.1
    	ucVlanMsgOnuPortEntry OBJECT-TYPE    
    		SYNTAX UcVlanMsgOnuPortEntry
    		MAX-ACCESS not-accessible
    		STATUS mandatory
    		DESCRIPTION ""
    		INDEX { ucVlanMsgOnuPortSlotIndex,ucVlanMsgOnuPortPonIndex,ucVlanMsgOnuPortOnuIndex,ucVlanMsgOnuPortIndex }
    	::= { ucVlanMsgOnuPortTable 1 }
    	
    	UcVlanMsgOnuPortEntry ::= SEQUENCE
    	{      
    		ucVlanMsgOnuPortSlotIndex	Integer32,
    		ucVlanMsgOnuPortPonIndex	Integer32,   
    		ucVlanMsgOnuPortOnuIndex    Integer32,
    		ucVlanMsgOnuPortIndex		Integer32,
    	    ucVlanMsgOnuPortVlan        OCTET STRING -- 1+x
    	}
    	   
   		-- 2.6.12.3.1.1.1
   		ucVlanMsgOnuPortSlotIndex OBJECT-TYPE
   	 		SYNTAX  Integer32 (1..16)
     		MAX-ACCESS  read-only
     		STATUS current
     		DESCRIPTION ""
   		::= { ucVlanMsgOnuPortEntry 1 }
   		
   		-- 2.6.12.3.1.1.2
   		ucVlanMsgOnuPortPonIndex OBJECT-TYPE
   	 		SYNTAX  Integer32 (1..32)
     		MAX-ACCESS  read-only
     		STATUS current
     		DESCRIPTION ""
   		::= { ucVlanMsgOnuPortEntry 2 }   
       	   
   		-- 2.6.12.3.1.1.3
   		ucVlanMsgOnuPortOnuIndex OBJECT-TYPE
   	 		SYNTAX  Integer32 (1..256)
     		MAX-ACCESS  read-only
     		STATUS current
     		DESCRIPTION ""
   		::= { ucVlanMsgOnuPortEntry 3 }
   		       
   		-- 2.6.12.3.1.1.4
   		ucVlanMsgOnuPortIndex OBJECT-TYPE
   	 		SYNTAX  Integer32 (1..16)
     		MAX-ACCESS  read-only
     		STATUS current
     		DESCRIPTION ""
   		::= { ucVlanMsgOnuPortEntry 4 }
   		
   		-- 2.6.12.3.1.1.5
   		ucVlanMsgOnuPortVlan OBJECT-TYPE
   	 		SYNTAX  OCTET STRING (SIZE(1..1024)) -- this size maybe TODO,not sure
     		MAX-ACCESS  read-write
     		STATUS current
     		DESCRIPTION 
     		"Length ------- info -----------------------------------------------------------
     		 1              Mode   0-CTC VLAN Transpare Mode, no parameters, see below TABLE
     		                       1-CTC VLAN Tag Mode, see below TABLE
     		                       2-CTC VLAN Translate Mode, see below TABLE
     		 (varies)       Parameters for VLAN, LENGTH Refer to below (varies) LENGTH REFER TABLE
     		                        

     		 ============================== (varies) LENGTH REFER TABLE ===============================
     		 CTC VLAN Mode Tag:
     		 Length       Description
     		 0            Transpare mode NO parameters
     		      		 
     		 CTC VLAN Mode Tag:
     		 Length       Description
     		 2            VLAN TPID
     		 2            VLAN Tag
     		 
     		 CTC VLAN Mode Translate:
     		 Length       Description
     		 2            VLAN TPID  (Default Vlan TPID)
     		 2            VLAN Tag   (Default Vlan TAG)                                       		 
     		 	          (Repeat the following fields once for each translation)
     		 2            VLAN TPID Old
     		 2            VLAN Tag Old
     		 2            VLAN TPID New
     		 2            VLAN Tag New
     		 "	     		 
   		::= { ucVlanMsgOnuPortEntry 5 }   		
   			                        
	            
	            
	-- 2.6.12.4 
	-- *********************** CLASSIFICATION MESSAGES ************************* 
	ucClassificationMsg OBJECT IDENTIFIER ::= { ucCTC 4 }
	   
	   
-- Table with OLT PORT index
    	-- 2.6.12.4.1
    	ucFilterMsgOltPortTable OBJECT-TYPE
    		SYNTAX SEQUENCE OF UcFilterMsgOltPortEntry
    		MAX-ACCESS not-accessible
    		STATUS mandatory
    		DESCRIPTION "" 
    	::= { ucClassificationMsg 1 }
    	
    	-- 2.6.12.4.1.1
    	ucFilterMsgOltPortEntry OBJECT-TYPE    
    		SYNTAX UcFilterMsgOltPortEntry
    		MAX-ACCESS not-accessible
    		STATUS mandatory
    		DESCRIPTION ""
    		INDEX { ucFilterMsgOltPortSlotIndex,ucFilterMsgOltPortIndex }
    	::= { ucFilterMsgOltPortTable 1 }
    	
    	UcFilterMsgOltPortEntry ::= SEQUENCE
    	{      
    		ucFilterMsgOltPortSlotIndex	Integer32,
    		ucFilterMsgOltPortIndex		Integer32,
    		ucFilterMsgOltPortClearClassification  Integer32,
    		ucFilterMsgOltPortGetClassification    OCTET STRING, -- 1+12n  TODO:
    		ucFilterMsgOltPortAddClassification    OCTET STRING, -- 1+12n  TODO:
    		ucFilterMsgOltPortDelClassification    OCTET STRING  -- 1+12n  TODO:
    	}
    	   
   		-- 2.6.12.4.1.1.1
   		ucFilterMsgOltPortSlotIndex OBJECT-TYPE
   	 		SYNTAX  Integer32 (1..16)
     		MAX-ACCESS  read-only
     		STATUS current
     		DESCRIPTION ""
   		::= { ucFilterMsgOltPortEntry 1 }
   		
   		-- 2.6.12.4.1.1.2
   		ucFilterMsgOltPortIndex OBJECT-TYPE
   	 		SYNTAX  Integer32 (1..16)
     		MAX-ACCESS  read-only
     		STATUS current
     		DESCRIPTION ""
   		::= { ucFilterMsgOltPortEntry 2 }
   		              
   		-- 2.6.12.4.1.1.3
   		ucFilterMsgOltPortClearClassification OBJECT-TYPE
   	 		SYNTAX  Integer32 {
   	 			none(0),
   	 			clear(1)
   	 		}
     		MAX-ACCESS  read-write
     		STATUS current
     		DESCRIPTION ""
   		::= { ucFilterMsgOltPortEntry 3 }  
   		
   		-- 2.6.12.4.1.1.4
   		ucFilterMsgOltPortGetClassification OBJECT-TYPE
   	 		SYNTAX  OCTET STRING (SIZE(1..1024)) -- this size maybe TODO,not sure
     		MAX-ACCESS  read-only
     		STATUS current
     		DESCRIPTION 
     		"Length --- info ------------------------------
     		1_          Number of times the rules structure repeats,The rule structure consists of the following fields
     		  |__ 1     Precedence
     		  |__ 1     Priority Marking, Path-Endpoint Queue
     		  |__ 1     Set 802.1d priority, 0xFF, do not set. For 0-7, change priority to that value
     		  |__ 1     Number of clauses,The following 3 fields repeat for each clause in this rule
     		      |__ 1    Refer to CTC Classification Operators, below Field for this clause 
     		      |__ 6    Value to match for this clause
     		      |__ 1    Refer to CTC Classification Fields, below Operator to use for this clause
     		         
     		           		
     		Refer Tables
     		
     		1. CTC Classification Operators:
     		   Value    Description
     		   0        Never Match
     		   1        Equal
     		   2        Not Equal
     		   3        Less than or equal
     		   4        Greater than or equal
     		   5        Field Exist
     		   6        Field Not Exist
     		   7        Always Match		   

     		2. CTC Classification Fields
     		   Value    Description      		   
     		   0        Destination MAC      		   
     		   1        Source MAC      		   
     		   2        VLAN Priority      		   
     		   3        VLAN ID
     		   4        Ethernet Type
     		   5        Path IP
     		   6        Source IP
     		   7        IP Version      		   
     		   8        IP TOS/DSCP
     		   9        IP Precedence
     		   10       Source L3 Port
     		   11       Path L3 Port
      		"     		
     	::= { ucFilterMsgOltPortEntry 4 }   		
   		   	
   		-- 2.6.12.4.1.1.5
   		ucFilterMsgOltPortAddClassification OBJECT-TYPE
   	 		SYNTAX  OCTET STRING (SIZE(1..1024)) -- this size maybe TODO,not sure
     		MAX-ACCESS  read-write
     		STATUS current
     		DESCRIPTION 
     		"Length --- info ------------------------------
     		1_          Number of times the rules structure repeats,The rule structure consists of the following fields
     		  |__ 1     Precedence
     		  |__ 1     Priority Marking, Path-Endpoint Queue
     		  |__ 1     Set 802.1d priority, 0xFF, do not set. For 0-7, change priority to that value
     		  |__ 1     Number of clauses,The following 3 fields repeat for each clause in this rule
     		      |__ 1    Refer to CTC Classification Operators, below Field for this clause 
     		      |__ 6    Value to match for this clause
     		      |__ 1    Refer to CTC Classification Fields, below Operator to use for this clause
     		         
     		           		
     		Refer Tables
     		
     		1. CTC Classification Operators:
     		   Value    Description
     		   0        Never Match
     		   1        Equal
     		   2        Not Equal
     		   3        Less than or equal
     		   4        Greater than or equal
     		   5        Field Exist
     		   6        Field Not Exist
     		   7        Always Match		   

     		2. CTC Classification Fields
     		   Value    Description      		   
     		   0        Destination MAC      		   
     		   1        Source MAC      		   
     		   2        VLAN Priority      		   
     		   3        VLAN ID
     		   4        Ethernet Type
     		   5        Path IP
     		   6        Source IP
     		   7        IP Version      		   
     		   8        IP TOS/DSCP
     		   9        IP Precedence
     		   10       Source L3 Port
     		   11       Path L3 Port
      		"
      		::= { ucFilterMsgOltPortEntry 5 }
     	
   		-- 2.6.12.4.1.1.6
   		ucFilterMsgOltPortDelClassification OBJECT-TYPE
   	 		SYNTAX  OCTET STRING (SIZE(1..1024)) -- this size maybe TODO,not sure
     		MAX-ACCESS  read-write
     		STATUS current
     		DESCRIPTION 
     		"Length --- info ------------------------------
     		1_          Number of times the rules structure repeats,The rule structure consists of the following fields
     		  |__ 1     Precedence
     		  |__ 1     Priority Marking, Path-Endpoint Queue
     		  |__ 1     Set 802.1d priority, 0xFF, do not set. For 0-7, change priority to that value
     		  |__ 1     Number of clauses,The following 3 fields repeat for each clause in this rule
     		      |__ 1    Refer to CTC Classification Operators, below Field for this clause 
     		      |__ 6    Value to match for this clause
     		      |__ 1    Refer to CTC Classification Fields, below Operator to use for this clause
     		         
     		           		
     		Refer Tables
     		
     		1. CTC Classification Operators:
     		   Value    Description
     		   0        Never Match
     		   1        Equal
     		   2        Not Equal
     		   3        Less than or equal
     		   4        Greater than or equal
     		   5        Field Exist
     		   6        Field Not Exist
     		   7        Always Match		   

     		2. CTC Classification Fields
     		   Value    Description      		   
     		   0        Destination MAC      		   
     		   1        Source MAC      		   
     		   2        VLAN Priority      		   
     		   3        VLAN ID
     		   4        Ethernet Type
     		   5        Path IP
     		   6        Source IP
     		   7        IP Version      		   
     		   8        IP TOS/DSCP
     		   9        IP Precedence
     		   10       Source L3 Port
     		   11       Path L3 Port
      		"
      		::= { ucFilterMsgOltPortEntry 6 }
     	
     	
     	
     	     	   		   		              
   		
-- Table with ONU PORT index
    	-- 2.6.12.4.2
    	ucFilterMsgOnuPortTable OBJECT-TYPE
    		SYNTAX SEQUENCE OF UcFilterMsgOnuPortEntry
    		MAX-ACCESS not-accessible
    		STATUS mandatory
    		DESCRIPTION "" 
    	::= { ucClassificationMsg 2 }
    	
    	-- 2.6.12.4.2.1
    	ucFilterMsgOnuPortEntry OBJECT-TYPE    
    		SYNTAX UcFilterMsgOnuPortEntry
    		MAX-ACCESS not-accessible
    		STATUS mandatory
    		DESCRIPTION ""
    		INDEX { ucFilterMsgOnuPortSlotIndex,ucFilterMsgOnuPortPonIndex,ucFilterMsgOnuPortOnuIndex,ucFilterMsgOnuPortIndex }
    	::= { ucFilterMsgOnuPortTable 1 }
    	
    	UcFilterMsgOnuPortEntry ::= SEQUENCE
    	{      
    		ucFilterMsgOnuPortSlotIndex	Integer32,
    		ucFilterMsgOnuPortPonIndex	Integer32,   
    		ucFilterMsgOnuPortOnuIndex  Integer32,
    		ucFilterMsgOnuPortIndex		Integer32,
    		ucFilterMsgOnuPortClearClassification  Integer32,
    		ucFilterMsgOnuPortGetClassification    OCTET STRING, -- 1+12n  TODO:
    		ucFilterMsgOnuPortAddClassification    OCTET STRING, -- 1+12n  TODO:
    		ucFilterMsgOnuPortDelClassification    OCTET STRING  -- 1+12n  TODO:    	
    	}
    	   
   		-- 2.6.12.4.2.1.1
   		ucFilterMsgOnuPortSlotIndex OBJECT-TYPE
   	 		SYNTAX  Integer32 (1..16)
     		MAX-ACCESS  read-only
     		STATUS current
     		DESCRIPTION ""
   		::= { ucFilterMsgOnuPortEntry 1 }
   		
   		-- 2.6.12.4.2.1.2
   		ucFilterMsgOnuPortPonIndex OBJECT-TYPE
   	 		SYNTAX  Integer32 (1..32)
     		MAX-ACCESS  read-only
     		STATUS current
     		DESCRIPTION ""
   		::= { ucFilterMsgOnuPortEntry 2 }   
       	   
   		-- 2.6.12.4.2.1.3
   		ucFilterMsgOnuPortOnuIndex OBJECT-TYPE
   	 		SYNTAX  Integer32 (1..256)
     		MAX-ACCESS  read-only
     		STATUS current
     		DESCRIPTION ""
   		::= { ucFilterMsgOnuPortEntry 3 }
   		       
   		-- 2.6.12.4.2.1.4
   		ucFilterMsgOnuPortIndex OBJECT-TYPE
   	 		SYNTAX  Integer32 (1..16)
     		MAX-ACCESS  read-only
     		STATUS current
     		DESCRIPTION ""
   		::= { ucFilterMsgOnuPortEntry 4 }
   		
   		--- 2.6.12.4.2.1.5
   		ucFilterMsgOnuPortClearClassification OBJECT-TYPE
   	 		SYNTAX  Integer32 {
   	 			none(0),
   	 			clear(1)
   	 		}
     		MAX-ACCESS  read-write
     		STATUS current
     		DESCRIPTION ""
   		::= { ucFilterMsgOnuPortEntry 5 }  
   		
   		-- 2.6.12.4.2.1.6
   		ucFilterMsgOnuPortGetClassification OBJECT-TYPE
   	 		SYNTAX  OCTET STRING (SIZE(1..1024)) -- this size maybe TODO,not sure
     		MAX-ACCESS  read-only
     		STATUS current
     		DESCRIPTION 
     		"Length --- info ------------------------------
     		1_          Number of times the rules structure repeats,The rule structure consists of the following fields
     		  |__ 1     Precedence
     		  |__ 1     Priority Marking, Path-Endpoint Queue
     		  |__ 1     Set 802.1d priority, 0xFF, do not set. For 0-7, change priority to that value
     		  |__ 1     Number of clauses,The following 3 fields repeat for each clause in this rule
     		      |__ 1    Refer to CTC Classification Operators, below Field for this clause 
     		      |__ 6    Value to match for this clause
     		      |__ 1    Refer to CTC Classification Fields, below Operator to use for this clause
     		         
     		           		
     		Refer Tables
     		
     		1. CTC Classification Operators:
     		   Value    Description
     		   0        Never Match
     		   1        Equal
     		   2        Not Equal
     		   3        Less than or equal
     		   4        Greater than or equal
     		   5        Field Exist
     		   6        Field Not Exist
     		   7        Always Match		   

     		2. CTC Classification Fields
     		   Value    Description      		   
     		   0        Destination MAC      		   
     		   1        Source MAC      		   
     		   2        VLAN Priority      		   
     		   3        VLAN ID
     		   4        Ethernet Type
     		   5        Path IP
     		   6        Source IP
     		   7        IP Version      		   
     		   8        IP TOS/DSCP
     		   9        IP Precedence
     		   10       Source L3 Port
     		   11       Path L3 Port
      		"    		
     	::= { ucFilterMsgOnuPortEntry 6 }   		
   		   	
   		-- 2.6.12.4.2.1.7
   		ucFilterMsgOnuPortAddClassification OBJECT-TYPE
   	 		SYNTAX  OCTET STRING (SIZE(1..1024)) -- this size maybe TODO,not sure
     		MAX-ACCESS  read-write
     		STATUS current
     		DESCRIPTION 
     		"Length --- info ------------------------------
     		1_          Number of times the rules structure repeats,The rule structure consists of the following fields
     		  |__ 1     Precedence
     		  |__ 1     Priority Marking, Path-Endpoint Queue
     		  |__ 1     Set 802.1d priority, 0xFF, do not set. For 0-7, change priority to that value
     		  |__ 1     Number of clauses,The following 3 fields repeat for each clause in this rule
     		      |__ 1    Refer to CTC Classification Operators, below Field for this clause 
     		      |__ 6    Value to match for this clause
     		      |__ 1    Refer to CTC Classification Fields, below Operator to use for this clause
     		         
     		           		
     		Refer Tables
     		
     		1. CTC Classification Operators:
     		   Value    Description
     		   0        Never Match
     		   1        Equal
     		   2        Not Equal
     		   3        Less than or equal
     		   4        Greater than or equal
     		   5        Field Exist
     		   6        Field Not Exist
     		   7        Always Match		   

     		2. CTC Classification Fields
     		   Value    Description      		   
     		   0        Destination MAC      		   
     		   1        Source MAC      		   
     		   2        VLAN Priority      		   
     		   3        VLAN ID
     		   4        Ethernet Type
     		   5        Path IP
     		   6        Source IP
     		   7        IP Version      		   
     		   8        IP TOS/DSCP
     		   9        IP Precedence
     		   10       Source L3 Port
     		   11       Path L3 Port
      		"
     	::= { ucFilterMsgOnuPortEntry 7 }
     	
   		-- 2.6.12.4.2.1.8
   		ucFilterMsgOnuPortDelClassification OBJECT-TYPE
   	 		SYNTAX  OCTET STRING (SIZE(1..1024)) -- this size maybe TODO,not sure
     		MAX-ACCESS  read-write
     		STATUS current
     		DESCRIPTION 
     		"Length --- info ------------------------------
     		1_          Number of times the rules structure repeats,The rule structure consists of the following fields
     		  |__ 1     Precedence
     		  |__ 1     Priority Marking, Path-Endpoint Queue
     		  |__ 1     Set 802.1d priority, 0xFF, do not set. For 0-7, change priority to that value
     		  |__ 1     Number of clauses,The following 3 fields repeat for each clause in this rule
     		      |__ 1    Refer to CTC Classification Operators, below Field for this clause 
     		      |__ 6    Value to match for this clause
     		      |__ 1    Refer to CTC Classification Fields, below Operator to use for this clause
     		         
     		           		
     		Refer Tables
     		
     		1. CTC Classification Operators:
     		   Value    Description
     		   0        Never Match
     		   1        Equal
     		   2        Not Equal
     		   3        Less than or equal
     		   4        Greater than or equal
     		   5        Field Exist
     		   6        Field Not Exist
     		   7        Always Match		   

     		2. CTC Classification Fields
     		   Value    Description      		   
     		   0        Destination MAC      		   
     		   1        Source MAC      		   
     		   2        VLAN Priority      		   
     		   3        VLAN ID
     		   4        Ethernet Type
     		   5        Path IP
     		   6        Source IP
     		   7        IP Version      		   
     		   8        IP TOS/DSCP
     		   9        IP Precedence
     		   10       Source L3 Port
     		   11       Path L3 Port
      		"
     	::= { ucFilterMsgOnuPortEntry 8 }   		
     	
     	
     	
     	
   			           
	           
	           	           
	-- 2.6.12.5
	-- ***************************** IGMP MESSAGES *****************************  
	ucIgmpMsg OBJECT IDENTIFIER ::= { ucCTC 5 }
						              
						              
-- Table with OLT PORT index
    	-- 2.6.12.5.1
    	ucIgmpMsgOltPortTable OBJECT-TYPE
    		SYNTAX SEQUENCE OF UcIgmpMsgOltPortEntry
    		MAX-ACCESS not-accessible
    		STATUS mandatory
    		DESCRIPTION "" 
    	::= { ucIgmpMsg 1 }
    	
    	-- 2.6.12.5.1.1
    	ucIgmpMsgOltPortEntry OBJECT-TYPE    
    		SYNTAX UcIgmpMsgOltPortEntry
    		MAX-ACCESS not-accessible
    		STATUS mandatory
    		DESCRIPTION ""
    		INDEX { ucIgmpMsgOltPortSlotIndex,ucIgmpMsgOltPortIndex }
    	::= { ucIgmpMsgOltPortTable 1 }
    	
    	UcIgmpMsgOltPortEntry ::= SEQUENCE
    	{      
    		ucIgmpMsgOltPortSlotIndex	Integer32,
    		ucIgmpMsgOltPortIndex		Integer32,
    		ucIgmpMsgOltPortGetMcastVlan   OCTET STRING,-- 2x 
    		ucIgmpMsgOltPortAddMcastVlan   OCTET STRING,-- 2x    	
    		ucIgmpMsgOltPortDelMcastVlan   OCTET STRING,-- 2x
    		ucIgmpMsgOltPortClrMcastVlan   Integer32,
    		ucIgmpMsgOltPortGetMcastGroups OCTET STRING,-- x
    		ucIgmpMsgOltPortAddMcastGroups OCTET STRING,-- 1+x
    		ucIgmpMsgOltPortDelMcastGroups OCTET STRING,-- 1+x 
    		ucIgmpMsgOltPortClrMcastGroups Integer32,
    		ucIgmpMsgOltPortGroupNumMax    Integer32, 
    		ucIgmpMsgOltPortMcastStripping OCTET STRING -- 2
    	}
    	   
   		-- 2.6.12.5.1.1.1
   		ucIgmpMsgOltPortSlotIndex OBJECT-TYPE
   	 		SYNTAX  Integer32 (1..16)
     		MAX-ACCESS  read-only
     		STATUS current
     		DESCRIPTION ""
   		::= { ucIgmpMsgOltPortEntry 1 }
   		
   		-- 2.6.12.5.1.1.2
   		ucIgmpMsgOltPortIndex OBJECT-TYPE
   	 		SYNTAX  Integer32 (1..16)
     		MAX-ACCESS  read-only
     		STATUS current
     		DESCRIPTION ""
   		::= { ucIgmpMsgOltPortEntry 2 }
   		
   		-- 2.6.12.5.1.1.3
   		ucIgmpMsgOltPortGetMcastVlan OBJECT-TYPE
   	 		SYNTAX  OCTET STRING (SIZE(1..1024))
     		MAX-ACCESS  read-only
     		STATUS current
     		DESCRIPTION 
     		"Length       Description
     		 (varies)     divisible by 2, A list of VLANs to add or delete, or in a Get message the VLANs retrieved from the ONU
     		"     		
   		::= { ucIgmpMsgOltPortEntry 3 }
   		                                
   		-- 2.6.12.5.1.1.4
   		ucIgmpMsgOltPortAddMcastVlan OBJECT-TYPE
   	 		SYNTAX  OCTET STRING (SIZE(1..1024))
     		MAX-ACCESS  read-write
     		STATUS current
     		DESCRIPTION 
     		"Length       Description
     		 (varies)     divisible by 2, A list of VLANs to add or delete, or in a Get message the VLANs retrieved from the ONU
     		"       		
   		::= { ucIgmpMsgOltPortEntry 4 }
   		
   		-- 2.6.12.5.1.1.5
   		ucIgmpMsgOltPortDelMcastVlan OBJECT-TYPE
   	 		SYNTAX  OCTET STRING (SIZE(1..1024))
     		MAX-ACCESS  read-write
     		STATUS current
     		DESCRIPTION 
     		"Length       Description
     		 (varies)     divisible by 2, A list of VLANs to add or delete, or in a Get message the VLANs retrieved from the ONU
     		"       		
   		::= { ucIgmpMsgOltPortEntry 5 }
   		            
   		-- 2.6.12.5.1.1.6
   		ucIgmpMsgOltPortClrMcastVlan OBJECT-TYPE
   	 		SYNTAX  Integer32 {
   	 			none(0),
   	 			clear(1)
   	 		}
     		MAX-ACCESS  read-write
     		STATUS current
     		DESCRIPTION ""
   		::= { ucIgmpMsgOltPortEntry 6 }   		            
   		   		   		                                
   		-- 2.6.12.5.1.1.7
   		ucIgmpMsgOltPortGetMcastGroups OBJECT-TYPE
   	 		SYNTAX  OCTET STRING (SIZE(1..1024))
     		MAX-ACCESS  read-only
     		STATUS current
     		DESCRIPTION 
     		"The following fields repeat once per group
     		 Length      Description
     		 1           Length of following data
     		 1           Type of label, Refer to the CTC Multicast Labels table below
     		 (varies)    These bytes are interpreted as a series of multicast labels of the type specified above
     		 
     		 Refer Tables
     		 =====================
     		 CTC Multicast Labels:
     		   Value   Description
     		   0       User Id (2 bytes) and Destination MAC (6 bytes)
     		   1       User Id (2 bytes) and Destination MAC (6 bytes) followed by VLAN ID (2 bytes)
     		   2       User Id (2 bytes) and Destination MAC (6 bytes) followed by Source MAC (6 bytes)     		 
     		"    		
   		::= { ucIgmpMsgOltPortEntry 7 }
   		
   		-- 2.6.12.5.1.1.8
   		ucIgmpMsgOltPortAddMcastGroups OBJECT-TYPE
   	 		SYNTAX  OCTET STRING (SIZE(1..1024))
     		MAX-ACCESS  read-write
     		STATUS current
     		DESCRIPTION 
     		"Length     Description
     		 1          Type of labels to follow,  Refer to the CTC Multicast Labels table below
     		 (varies)   These bytes are interpreted as a series of multicast labels of the type specified above
     		
     		 Refer Tables
     		 =====================
     		 CTC Multicast Labels:
     		   Value   Description
     		   0       User Id (2 bytes) and Destination MAC (6 bytes)
     		   1       User Id (2 bytes) and Destination MAC (6 bytes) followed by VLAN ID (2 bytes)
     		   2       User Id (2 bytes) and Destination MAC (6 bytes) followed by Source MAC (6 bytes)
     		"    		 
   		::= { ucIgmpMsgOltPortEntry 8 }
   		
   		-- 2.6.12.5.1.1.9
   		ucIgmpMsgOltPortDelMcastGroups OBJECT-TYPE
   	 		SYNTAX  OCTET STRING (SIZE(1..1024))
     		MAX-ACCESS  read-write
     		STATUS current
     		DESCRIPTION
     		"Length     Description
     		 1          Type of labels to follow,  Refer to the CTC Multicast Labels table below
     		 (varies)   These bytes are interpreted as a series of multicast labels of the type specified above
     		
     		 Refer Tables
     		 =====================
     		 CTC Multicast Labels:
     		   Value   Description
     		   0       User Id (2 bytes) and Destination MAC (6 bytes)
     		   1       User Id (2 bytes) and Destination MAC (6 bytes) followed by VLAN ID (2 bytes)
     		   2       User Id (2 bytes) and Destination MAC (6 bytes) followed by Source MAC (6 bytes)
     		"       		
   		::= { ucIgmpMsgOltPortEntry 9 }   		   		   		
   		              
   		-- 2.6.12.5.1.1.10
   		ucIgmpMsgOltPortClrMcastGroups OBJECT-TYPE
   	 		SYNTAX  Integer32 {
   	 			none(0),
   	 			clear(1)
   	 		}
     		MAX-ACCESS  read-write
     		STATUS current
     		DESCRIPTION ""
   		::= { ucIgmpMsgOltPortEntry 10 }   		              
   		
   		-- 2.6.12.5.1.1.11
   		ucIgmpMsgOltPortGroupNumMax OBJECT-TYPE
   	 		SYNTAX  Integer32 (0..4095)   -- TODO:
   	 		MAX-ACCESS  read-write
     		STATUS current
     		DESCRIPTION 
     		"Maximum number of groups that this port can join simultaneously,
     		When the EPON port is specified, this specifies a global max for the number 
     		of multicast streams that the ONU can receive
     		15.6.3.5 CTC Get/Set Group Number Max (Message IDs: 282 & 283)"
   		::= { ucIgmpMsgOltPortEntry 11 }   		   		        
   		   		        
   		-- 2.6.12.5.1.1.12
   		ucIgmpMsgOltPortMcastStripping OBJECT-TYPE
   	 		SYNTAX  OCTET STRING (SIZE(1..2))
     		MAX-ACCESS  read-write
     		STATUS current
     		DESCRIPTION 
     		"Length     Description
     		 1          Reserved, set to zero
     		 1          Strip VLAN tag: (1)strip, (0)keep tag
     		 "     		
   		::= { ucIgmpMsgOltPortEntry 12 }   		   		        
   		   		        
   		   		        
   		   		        
   		   		        
   		   		        
   		   		        
   		   		        
   		   		        
-- Table with ONU PORT index
    	-- 2.6.12.5.2
    	ucIgmpMsgOnuPortTable OBJECT-TYPE
    		SYNTAX SEQUENCE OF UcIgmpMsgOnuPortEntry
    		MAX-ACCESS not-accessible
    		STATUS mandatory
    		DESCRIPTION "" 
    	::= { ucIgmpMsg 2 }
    	
    	-- 2.6.12.5.2.1
    	ucIgmpMsgOnuPortEntry OBJECT-TYPE    
    		SYNTAX UcIgmpMsgOnuPortEntry
    		MAX-ACCESS not-accessible
    		STATUS mandatory
    		DESCRIPTION ""
    		INDEX { ucIgmpMsgOnuPortSlotIndex,ucIgmpMsgOnuPortPonIndex,ucIgmpMsgOnuPortOnuIndex,ucIgmpMsgOnuPortIndex }
    	::= { ucIgmpMsgOnuPortTable 1 }
    	
    	UcIgmpMsgOnuPortEntry ::= SEQUENCE
    	{      
    		ucIgmpMsgOnuPortSlotIndex	Integer32,
    		ucIgmpMsgOnuPortPonIndex	Integer32,   
    		ucIgmpMsgOnuPortOnuIndex  Integer32,
    		ucIgmpMsgOnuPortIndex		Integer32,
    		ucIgmpMsgOnuPortGetMcastVlan   OCTET STRING,-- 2x 
    		ucIgmpMsgOnuPortAddMcastVlan   OCTET STRING,-- 2x    	
    		ucIgmpMsgOnuPortDelMcastVlan   OCTET STRING,-- 2x
    		ucIgmpMsgOnuPortClrMcastVlan   Integer32,
    		ucIgmpMsgOnuPortGetMcastGroups OCTET STRING,-- x
    		ucIgmpMsgOnuPortAddMcastGroups OCTET STRING,-- 1+x
    		ucIgmpMsgOnuPortDelMcastGroups OCTET STRING,-- 1+x 
    		ucIgmpMsgOnuPortClrMcastGroups Integer32,
    		ucIgmpMsgOnuPortGroupNumMax    Integer32, 
    		ucIgmpMsgOnuPortMcastStripping OCTET STRING -- 2
    	}
    	   
   		-- 2.6.12.5.2.1.1
   		ucIgmpMsgOnuPortSlotIndex OBJECT-TYPE
   	 		SYNTAX  Integer32 (1..16)
     		MAX-ACCESS  read-only
     		STATUS current
     		DESCRIPTION ""
   		::= { ucIgmpMsgOnuPortEntry 1 }
   		
   		-- 2.6.12.5.2.1.2
   		ucIgmpMsgOnuPortPonIndex OBJECT-TYPE
   	 		SYNTAX  Integer32 (1..32)
     		MAX-ACCESS  read-only
     		STATUS current
     		DESCRIPTION ""
   		::= { ucIgmpMsgOnuPortEntry 2 }   
       	   
   		-- 2.6.12.5.2.1.3
   		ucIgmpMsgOnuPortOnuIndex OBJECT-TYPE
   	 		SYNTAX  Integer32 (1..256)
     		MAX-ACCESS  read-only
     		STATUS current
     		DESCRIPTION ""
   		::= { ucIgmpMsgOnuPortEntry 3 }
   		       
   		-- 2.6.12.5.2.1.4
   		ucIgmpMsgOnuPortIndex OBJECT-TYPE
   	 		SYNTAX  Integer32 (1..16)
     		MAX-ACCESS  read-only
     		STATUS current
     		DESCRIPTION ""
   		::= { ucIgmpMsgOnuPortEntry 4 }

   		-- 2.6.12.5.2.1.5
   		ucIgmpMsgOnuPortGetMcastVlan OBJECT-TYPE
   	 		SYNTAX  OCTET STRING (SIZE(1..1024))
     		MAX-ACCESS  read-only
     		STATUS current
     		DESCRIPTION 
     		"Length       Description
     		 (varies)     divisible by 2, A list of VLANs to add or delete, or in a Get message the VLANs retrieved from the ONU
     		"     		
   		::= { ucIgmpMsgOnuPortEntry 5 }
   		                                
   		-- 2.6.12.5.2.1.6
   		ucIgmpMsgOnuPortAddMcastVlan OBJECT-TYPE
   	 		SYNTAX  OCTET STRING (SIZE(1..1024))
     		MAX-ACCESS  read-write
     		STATUS current
     		DESCRIPTION 
     		"Length       Description
     		 (varies)     divisible by 2, A list of VLANs to add or delete, or in a Get message the VLANs retrieved from the ONU
     		"       		
   		::= { ucIgmpMsgOnuPortEntry 6 }
   		
   		-- 2.6.12.5.2.1.7
   		ucIgmpMsgOnuPortDelMcastVlan OBJECT-TYPE
   	 		SYNTAX  OCTET STRING (SIZE(1..1024))
     		MAX-ACCESS  read-write
     		STATUS current
     		DESCRIPTION 
     		"Length       Description
     		 (varies)     divisible by 2, A list of VLANs to add or delete, or in a Get message the VLANs retrieved from the ONU
     		"       		
   		::= { ucIgmpMsgOnuPortEntry 7 }
   		            
   		-- 2.6.12.5.2.1.8
   		ucIgmpMsgOnuPortClrMcastVlan OBJECT-TYPE
   	 		SYNTAX  Integer32 {
   	 			none(0),
   	 			clear(1)
   	 		}
     		MAX-ACCESS  read-write
     		STATUS current
     		DESCRIPTION ""
   		::= { ucIgmpMsgOnuPortEntry 8 }   		            
   		   		   		                                
   		-- 2.6.12.5.2.1.9
   		ucIgmpMsgOnuPortGetMcastGroups OBJECT-TYPE
   	 		SYNTAX  OCTET STRING (SIZE(1..1024))
     		MAX-ACCESS  read-only
     		STATUS current
     		DESCRIPTION 
     		"The following fields repeat once per group
     		 Length      Description
     		 1           Length of following data
     		 1           Type of label, Refer to the CTC Multicast Labels table below
     		 (varies)    These bytes are interpreted as a series of multicast labels of the type specified above
     		 
     		 Refer Tables
     		 =====================
     		 CTC Multicast Labels:
     		   Value   Description
     		   0       User Id (2 bytes) and Destination MAC (6 bytes)
     		   1       User Id (2 bytes) and Destination MAC (6 bytes) followed by VLAN ID (2 bytes)
     		   2       User Id (2 bytes) and Destination MAC (6 bytes) followed by Source MAC (6 bytes)     		 
     		"    		
   		::= { ucIgmpMsgOnuPortEntry 9 }
   		
   		-- 2.6.12.5.2.1.10
   		ucIgmpMsgOnuPortAddMcastGroups OBJECT-TYPE
   	 		SYNTAX  OCTET STRING (SIZE(1..1024))
     		MAX-ACCESS  read-write
     		STATUS current
     		DESCRIPTION 
     		"Length     Description
     		 1          Type of labels to follow,  Refer to the CTC Multicast Labels table below
     		 (varies)   These bytes are interpreted as a series of multicast labels of the type specified above
     		
     		 Refer Tables
     		 =====================
     		 CTC Multicast Labels:
     		   Value   Description
     		   0       User Id (2 bytes) and Destination MAC (6 bytes)
     		   1       User Id (2 bytes) and Destination MAC (6 bytes) followed by VLAN ID (2 bytes)
     		   2       User Id (2 bytes) and Destination MAC (6 bytes) followed by Source MAC (6 bytes)
     		"    		 
   		::= { ucIgmpMsgOnuPortEntry 10 }
   		
   		-- 2.6.12.5.2.1.11
   		ucIgmpMsgOnuPortDelMcastGroups OBJECT-TYPE
   	 		SYNTAX  OCTET STRING (SIZE(1..1024))
     		MAX-ACCESS  read-write
     		STATUS current
     		DESCRIPTION
     		"Length     Description
     		 1          Type of labels to follow,  Refer to the CTC Multicast Labels table below
     		 (varies)   These bytes are interpreted as a series of multicast labels of the type specified above
     		
     		 Refer Tables
     		 =====================
     		 CTC Multicast Labels:
     		   Value   Description
     		   0       User Id (2 bytes) and Destination MAC (6 bytes)
     		   1       User Id (2 bytes) and Destination MAC (6 bytes) followed by VLAN ID (2 bytes)
     		   2       User Id (2 bytes) and Destination MAC (6 bytes) followed by Source MAC (6 bytes)
     		"       		
   		::= { ucIgmpMsgOnuPortEntry 11 }   		   		   		
   		              
   		-- 2.6.12.5.2.1.12
   		ucIgmpMsgOnuPortClrMcastGroups OBJECT-TYPE
   	 		SYNTAX  Integer32 {
   	 			none(0),
   	 			clear(1)
   	 		}
     		MAX-ACCESS  read-write
     		STATUS current
     		DESCRIPTION ""
   		::= { ucIgmpMsgOnuPortEntry 12 }   		              
   		
   		-- 2.6.12.5.2.1.13
   		ucIgmpMsgOnuPortGroupNumMax OBJECT-TYPE
   	 		SYNTAX  Integer32 (0..4095)   -- TODO:
   	 		MAX-ACCESS  read-write
     		STATUS current
     		DESCRIPTION 
     		"Maximum number of groups that this port can join simultaneously,
     		When the EPON port is specified, this specifies a global max for the number 
     		of multicast streams that the ONU can receive
     		15.6.3.5 CTC Get/Set Group Number Max (Message IDs: 282 & 283)"
   		::= { ucIgmpMsgOnuPortEntry 13 }   		   		        
   		   		        
   		-- 2.6.12.5.2.1.14
   		ucIgmpMsgOnuPortMcastStripping OBJECT-TYPE
   	 		SYNTAX  OCTET STRING (SIZE(1..2))
     		MAX-ACCESS  read-write
     		STATUS current
     		DESCRIPTION 
     		"Length     Description
     		 1          Reserved, set to zero
     		 1          Strip VLAN tag: (1)strip, (0)keep tag
     		 "     		
   		::= { ucIgmpMsgOnuPortEntry 14 }
   		
   		
   		
   		
   		
         
-- Table with ONU index
    	-- 2.6.12.5.3
    	ucIgmpMsgOnuTable OBJECT-TYPE
    		SYNTAX SEQUENCE OF UcIgmpMsgOnuEntry
    		MAX-ACCESS not-accessible
    		STATUS mandatory
    		DESCRIPTION "" 
    	::= { ucIgmpMsg 3 }
    	
    	-- 2.6.12.5.3.1
    	ucIgmpMsgOnuEntry OBJECT-TYPE    
    		SYNTAX UcIgmpMsgOnuEntry
    		MAX-ACCESS not-accessible
    		STATUS mandatory
    		DESCRIPTION ""
    		INDEX { ucIgmpMsgOnuSlotIndex,ucIgmpMsgOnuPonIndex,ucIgmpMsgOnuIndex }
    	::= { ucIgmpMsgOnuTable 1 }
    	
    	UcIgmpMsgOnuEntry ::= SEQUENCE
    	{      
    		ucIgmpMsgOnuSlotIndex	Integer32,
    		ucIgmpMsgOnuPonIndex	Integer32,   
    		ucIgmpMsgOnuIndex       Integer32,
    		ucIgmpMsgOnuMcastMode   Integer32,
    		ucIgmpMsgOnuGetFastLeaveAbility  Integer32,
    		ucIgmpMsgOnuGetFastLeaveState    Integer32,
    		ucIgmpMsgOnuSetFastLeaveControl  Integer32    	
    	}
    	   
   		-- 2.6.12.5.3.1.1
   		ucIgmpMsgOnuSlotIndex OBJECT-TYPE
   	 		SYNTAX  Integer32 (1..16)
     		MAX-ACCESS  read-only
     		STATUS current
     		DESCRIPTION ""
   		::= { ucIgmpMsgOnuEntry 1 }
   		
   		-- 2.6.12.5.3.1.2
   		ucIgmpMsgOnuPonIndex OBJECT-TYPE
   	 		SYNTAX  Integer32 (1..32)
     		MAX-ACCESS  read-only
     		STATUS current
     		DESCRIPTION ""
   		::= { ucIgmpMsgOnuEntry 2 }   
       	   
   		-- 2.6.12.5.3.1.3
   		ucIgmpMsgOnuIndex OBJECT-TYPE
   	 		SYNTAX  Integer32 (1..256)
     		MAX-ACCESS  read-only
     		STATUS current
     		DESCRIPTION ""
   		::= { ucIgmpMsgOnuEntry 3 }     
              
   		-- 2.6.12.5.3.1.4
   		ucIgmpMsgOnuMcastMode OBJECT-TYPE
   	 		SYNTAX  Integer32 {
   	 			notCtcMode(0),
   	 			ctcMode(1)
   	 		}
     		MAX-ACCESS  read-write
     		STATUS current
     		DESCRIPTION 
     		"Switching mode, (0)IGMP snooping mode, (1)CTC controllable IGMP mode, snooping disabled"
   		::= { ucIgmpMsgOnuEntry 4 }
   		
   		-- 2.6.12.5.3.1.5
   		ucIgmpMsgOnuGetFastLeaveAbility OBJECT-TYPE
   	 		SYNTAX  Integer32 (0..16)
     		MAX-ACCESS  read-only
     		STATUS current
     		DESCRIPTION 
     		"Ability bitmap, 
     		Bit 0 – support Non-Fast-Leave when in IGMP snooping mod
     		Bit 1 – support Fast-Leave when in IGMP snooping mode
     		Bit 2 – support Non-Fast-Leave when in CTC Controlled IGMP mode
     		Bit 3 – support Fast-Leave when in CTC Controlled IGMP Mod"
   		::= { ucIgmpMsgOnuEntry 5 }
   		
   		-- 2.6.12.5.3.1.6
   		ucIgmpMsgOnuGetFastLeaveState OBJECT-TYPE
   	 		SYNTAX  Integer32 {
   	 			disabled(1),
   	 			enabled(2)
   	 		}
     		MAX-ACCESS  read-only
     		STATUS current
     		DESCRIPTION 
     		"Fast Leave state, (1)disabled  (2)enabled"
   		::= { ucIgmpMsgOnuEntry 6 }
   		
   		-- 2.6.12.5.3.1.7
   		ucIgmpMsgOnuSetFastLeaveControl OBJECT-TYPE
   	 		SYNTAX  Integer32 {
   	 			deactivate(1),
   	 			activate(2)
   	 		}
   	 		MAX-ACCESS  read-write
     		STATUS current
     		DESCRIPTION 
     		"Fast Leave control, (1)deactivate Fast Leave Function  
     		                     (2)activate Fast Leave Function"      		
   		::= { ucIgmpMsgOnuEntry 7 }   		   		   		              
   		   		              

	-- Add CTC Controlable IGMP Manage Mib Branch !!!  
	-- 2011.09.20-Linker-HiOSO			                     
    -- 2.6.13
	ucCTCIgmp OBJECT IDENTIFIER ::= { ucPon 13 }
	              
	-- 2.6.13.1   
	ucOltIgmpGroups OBJECT IDENTIFIER ::= { ucCTCIgmp 1 }      
	-- 2.6.13.1.1   
	ucOltMultiVlan OBJECT IDENTIFIER ::= { ucOltIgmpGroups 1 }		                                          
    -- Olt Igmp Multicast Vlans Table
    	-- 2.6.13.1.1.1
    	ucOltMultiVlanTable OBJECT-TYPE
    		SYNTAX SEQUENCE OF UcOltMultiVlanEntry
    		MAX-ACCESS not-accessible
    		STATUS mandatory
    		DESCRIPTION "" 
    	::= { ucOltMultiVlan 1 }
    	
    	-- 2.6.13.1.1.1.1
    	ucOltMultiVlanEntry OBJECT-TYPE    
    		SYNTAX UcOltMultiVlanEntry
    		MAX-ACCESS not-accessible
    		STATUS mandatory
    		DESCRIPTION ""
    		INDEX { ucOltMultiVlanSlotIndex}
    	::= { ucOltMultiVlanTable 1 }
    	
    	UcOltMultiVlanEntry ::= SEQUENCE {      
    		ucOltMultiVlanSlotIndex	      Integer32,    	    
    	    ucOltMultiVlansGet            OCTET STRING,
    	    ucOltMultiVlansAdd            OCTET STRING,
    	    ucOltMultiVlansDel            OCTET STRING
    	}
    	
   		ucOltMultiVlanSlotIndex OBJECT-TYPE
   	 		SYNTAX  Integer32 (1..16)
     		MAX-ACCESS  read-only
     		STATUS current
     		DESCRIPTION ""
   		::= { ucOltMultiVlanEntry 1 }
   		
   		ucOltMultiVlansGet OBJECT-TYPE
   	 		SYNTAX  OCTET STRING (SIZE(0..1024))
     		MAX-ACCESS  read-only
     		STATUS current
     		DESCRIPTION
     		"Size ---- Description -------------------------------------------
     		 1          Number of queue sets, Number of times the following fields repeat
     		      ############################################################################################
     		      2     Multicast Network VLAN ID, which for frames come from up igmp-router or switch to tag
     		      2     Multicast User VLAN ID, this tag will translate to ONU, ONU may untag or tag with this VID to user"
   		::= { ucOltMultiVlanEntry 2 }
   		
   		ucOltMultiVlansAdd OBJECT-TYPE
   	 		SYNTAX  OCTET STRING (SIZE(0..1024))
     		MAX-ACCESS  read-write
     		STATUS current
     		DESCRIPTION
     		"Size ---- Description -------------------------------------------
     		 1          Number of queue sets, Number of times the following fields repeat
     		      ############################################################################################
     		      2     Multicast Network VLAN ID, which for frames come from up igmp-router or switch to tag
     		      2     Multicast User VLAN ID, this tag will translate to ONU, ONU may untag or tag with this VID to user"
   		::= { ucOltMultiVlanEntry 3 }
   		
   		ucOltMultiVlansDel OBJECT-TYPE
   	 		SYNTAX  OCTET STRING (SIZE(0..1024))
     		MAX-ACCESS  read-write
     		STATUS current
     		DESCRIPTION
     		"Size ---- Description -------------------------------------------
     		 1          Number of queue sets, Number of times the following fields repeat
     		      ############################################################################################
     		      2     Multicast Network VLAN ID, which for frames come from up igmp-router or switch to tag
     		      2     Multicast User VLAN ID, this tag will translate to ONU, ONU may untag or tag with this VID to user"
   		::= { ucOltMultiVlanEntry 4 }   		   				   		
                            
                            
                            
                            

	-- 2.6.13.1.2 
	ucOltMultiGroup OBJECT IDENTIFIER ::= { ucOltIgmpGroups 2 }
    -- Olt Igmp Multicast Groups Configure Table
    	-- 2.6.13.1.2.1
    	ucOltMultiGroupTable OBJECT-TYPE
    		SYNTAX SEQUENCE OF UcOltMultiGroupEntry
    		MAX-ACCESS not-accessible
    		STATUS mandatory
    		DESCRIPTION "" 
    	::= { ucOltMultiGroup 1 }
    	
    	-- 2.6.13.1.2.1.1
    	ucOltMultiGroupEntry OBJECT-TYPE    
    		SYNTAX UcOltMultiGroupEntry
    		MAX-ACCESS not-accessible
    		STATUS mandatory
    		DESCRIPTION ""
    		INDEX { ucOltMultiGroupSlotIndex}
    	::= { ucOltMultiGroupTable 1 }
    	
    	UcOltMultiGroupEntry ::= SEQUENCE {      
    		ucOltMultiGroupSlotIndex	       Integer32,
    	    ucOltMultiGroupIpAddrGet           OCTET STRING,
    	    ucOltMultiGroupIpAddrAdd           OCTET STRING,
    	    ucOltMultiGroupIpAddrDel           OCTET STRING,
    	    ucOltMultiGroupProxyIp             IpAddress
    	}
    	
   		ucOltMultiGroupSlotIndex OBJECT-TYPE
   	 		SYNTAX  Integer32 (1..16)
     		MAX-ACCESS  read-only
     		STATUS current
     		DESCRIPTION ""
   		::= { ucOltMultiGroupEntry 1 }
   		
   		ucOltMultiGroupIpAddrGet OBJECT-TYPE
   	 		SYNTAX  OCTET STRING (SIZE(0..1024))
     		MAX-ACCESS  read-only
     		STATUS current
     		DESCRIPTION
     		"Size ---- Description -------------------------------------------
     		 1          Number of queue sets, Number of times the following fields repeat
     		      ############################################################################################
     		      2     Multicast Network VLAN ID, which for frames come from up igmp-router or switch to tag
     		      4     Multicast Group Ip Address"
   		::= { ucOltMultiGroupEntry 2 } 
   		
   		ucOltMultiGroupIpAddrAdd OBJECT-TYPE
   	 		SYNTAX  OCTET STRING (SIZE(0..1024))
     		MAX-ACCESS  read-write
     		STATUS current
     		DESCRIPTION
     		"Size ---- Description -------------------------------------------
     		 1          Number of queue sets, Number of times the following fields repeat
     		      ############################################################################################
     		      2     Multicast Network VLAN ID, which for frames come from up igmp-router or switch to tag
     		      4     Multicast Group Ip Address"
   		::= { ucOltMultiGroupEntry 3 }
   		
   		ucOltMultiGroupIpAddrDel OBJECT-TYPE
   	 		SYNTAX  OCTET STRING (SIZE(0..1024))
     		MAX-ACCESS  read-write
     		STATUS current
     		DESCRIPTION
     		"Size ---- Description -------------------------------------------
     		 1          Number of queue sets, Number of times the following fields repeat
     		      ############################################################################################
     		      2     Multicast Network VLAN ID, which for frames come from up igmp-router or switch to tag
     		      4     Multicast Group Ip Address"
   		::= { ucOltMultiGroupEntry 4 }
   		
   		ucOltMultiGroupProxyIp OBJECT-TYPE
   	 		SYNTAX  IpAddress
     		MAX-ACCESS  read-write
     		STATUS current
     		DESCRIPTION ""
     	::= { ucOltMultiGroupEntry 5 }   				   				
	                  
         
        -- ============== ucOltMultiGroupStatusTable ===========
    	-- 2.6.13.1.2.2
    	ucOltMultiGroupStatusTable OBJECT-TYPE
    		SYNTAX SEQUENCE OF UcOltMultiGroupStatusEntry
    		MAX-ACCESS not-accessible
    		STATUS mandatory
    		DESCRIPTION "" 
    	::= { ucOltMultiGroup 2 }
    	
    	-- 2.6.13.1.2.2.1
    	ucOltMultiGroupStatusEntry OBJECT-TYPE    
    		SYNTAX UcOltMultiGroupStatusEntry
    		MAX-ACCESS not-accessible
    		STATUS mandatory
    		DESCRIPTION ""
    		INDEX { ucOltMultiGroupStatusSlotIndex}
    	::= { ucOltMultiGroupStatusTable 1 }
    	
    	UcOltMultiGroupStatusEntry ::= SEQUENCE {      
    		ucOltMultiGroupStatusSlotIndex	       Integer32,
    	    ucOltMultiGroupStatus                  OCTET STRING
    	}
    	
   		ucOltMultiGroupStatusSlotIndex OBJECT-TYPE
   	 		SYNTAX  Integer32 (1..16)
     		MAX-ACCESS  read-only
     		STATUS current
     		DESCRIPTION ""
   		::= { ucOltMultiGroupStatusEntry 1 }
   		
   		ucOltMultiGroupStatus OBJECT-TYPE
   	 		SYNTAX  OCTET STRING (SIZE(0..1024))
     		MAX-ACCESS  read-only
     		STATUS current
     		DESCRIPTION
     		"Size ---- Description -------------------------------------------
     		 1          Number of queue sets, Number of times the following fields repeat
     		      ############################################################################################
     		      2     Multicast Network VLAN ID, which for frames come from up igmp-router or switch to tag
     		      4     Multicast Group Ip Address"
   		::= { ucOltMultiGroupStatusEntry 2 }
   		
   		
   			                  
	                  

                     
	-- 2.6.13.2
	ucOnuIgmpGroups OBJECT IDENTIFIER ::= { ucCTCIgmp 2 }	    
	-- 2.6.13.2.1
	ucOnuGroupsCfg OBJECT IDENTIFIER ::= { ucOnuIgmpGroups 1 }
    -- Configure Onu Igmp Multicast Groups with VID
    	-- 2.6.13.2.1.1
    	ucOnuGroupsCfgTable OBJECT-TYPE
    		SYNTAX SEQUENCE OF UcOnuGroupsCfgEntry
    		MAX-ACCESS not-accessible
    		STATUS mandatory
    		DESCRIPTION "" 
    	::= { ucOnuGroupsCfg 1 }
    	
    	-- 2.6.13.2.1.1.1
    	ucOnuGroupsCfgEntry OBJECT-TYPE    
    		SYNTAX UcOnuGroupsCfgEntry
    		MAX-ACCESS not-accessible
    		STATUS mandatory
    		DESCRIPTION ""
    		INDEX { ucOnuGroupsCfgSlotIndex,
    		        ucOnuGroupsCfgPonIndex,
    		        ucOnuGroupsCfgOnuIndex,
    		        ucOnuGroupsCfgPortIndex }
    	::= { ucOnuGroupsCfgTable 1 }
    	
    	UcOnuGroupsCfgEntry ::= SEQUENCE
    	{      
    		ucOnuGroupsCfgSlotIndex		Integer32,
    		ucOnuGroupsCfgPonIndex		Integer32,
    		ucOnuGroupsCfgOnuIndex		Integer32,
    	    ucOnuGroupsCfgPortIndex     Integer32,
    	    ucOnuGroupsCfgGroupsGet     OCTET STRING,
    	    ucOnuGroupsCfgGroupsAdd     OCTET STRING,
    	    ucOnuGroupsCfgGroupsDel     OCTET STRING
    	}
    	
   		ucOnuGroupsCfgSlotIndex OBJECT-TYPE
   	 		SYNTAX  Integer32 (1..16)
     		MAX-ACCESS  read-only
     		STATUS current
     		DESCRIPTION ""
   		::= { ucOnuGroupsCfgEntry 1 }
   		
   		ucOnuGroupsCfgPonIndex OBJECT-TYPE
   	 		SYNTAX  Integer32 (1..32)
     		MAX-ACCESS  read-only
     		STATUS current
     		DESCRIPTION ""
   		::= { ucOnuGroupsCfgEntry 2 }   
       	   
   		ucOnuGroupsCfgOnuIndex OBJECT-TYPE
   	 		SYNTAX  Integer32 (1..256)
     		MAX-ACCESS  read-only
     		STATUS current
     		DESCRIPTION ""
   		::= { ucOnuGroupsCfgEntry 3 }
                      
   		ucOnuGroupsCfgPortIndex OBJECT-TYPE
   	 		SYNTAX  Integer32 (1..256)
     		MAX-ACCESS  read-only
     		STATUS current
     		DESCRIPTION ""
   		::= { ucOnuGroupsCfgEntry 4 }
           
   		ucOnuGroupsCfgGroupsGet OBJECT-TYPE
   	 		SYNTAX  OCTET STRING (SIZE(0..1024))
     		MAX-ACCESS  read-only
     		STATUS current
     		DESCRIPTION
     		"Size ---- Description -------------------------------------------
     		 1          Number of queue sets, Number of times the following fields repeat
     		      #######################################################################
     		      2     Multicast VLAN ID
     		      6     Multicast Group Mac Address"    		 
     	::= { ucOnuGroupsCfgEntry 5 }
     	
   		ucOnuGroupsCfgGroupsAdd OBJECT-TYPE
   	 		SYNTAX  OCTET STRING (SIZE(0..1024))
     		MAX-ACCESS  read-write
     		STATUS current
     		DESCRIPTION
     		"Size ---- Description -------------------------------------------
     		 1          Number of queue sets, Number of times the following fields repeat
     		      #######################################################################
     		      2     Multicast VLAN ID
     		      6     Multicast Group Mac Address"    		 
     	::= { ucOnuGroupsCfgEntry 6 }
     	
   		ucOnuGroupsCfgGroupsDel OBJECT-TYPE
   	 		SYNTAX  OCTET STRING (SIZE(0..1024))
     		MAX-ACCESS  read-write
     		STATUS current
     		DESCRIPTION
     		"Size ---- Description -------------------------------------------
     		 1          Number of queue sets, Number of times the following fields repeat
     		      #######################################################################
     		      2     Multicast VLAN ID
     		      6     Multicast Group Mac Address"    		 
     	::= { ucOnuGroupsCfgEntry 7 }
     	           
                            
                            
                              	           
     	
     	
     	     	           
     	                 
     	-- Onu Multicast stream strip tag or remain tag output tabel
    	-- 2.6.13.2.1.2
    	ucOnuMcastStripTable OBJECT-TYPE
    		SYNTAX SEQUENCE OF UcOnuMcastStripEntry
    		MAX-ACCESS not-accessible
    		STATUS mandatory
    		DESCRIPTION "" 
    	::= { ucOnuGroupsCfg 2 }
    	
    	-- 2.6.13.2.1.2.1
    	ucOnuMcastStripEntry OBJECT-TYPE    
    		SYNTAX UcOnuMcastStripEntry
    		MAX-ACCESS not-accessible
    		STATUS mandatory
    		DESCRIPTION ""
    		INDEX { ucOnuMcastStripSlotIndex,ucOnuMcastStripPonIndex,ucOnuMcastStripOnuIndex,ucOnuMcastStripPortIndex }
    	::= { ucOnuMcastStripTable 1 }
    	
    	UcOnuMcastStripEntry ::= SEQUENCE
    	{      
    		ucOnuMcastStripSlotIndex		Integer32,
    		ucOnuMcastStripPonIndex			Integer32,
    		ucOnuMcastStripOnuIndex			Integer32,
    	    ucOnuMcastStripPortIndex      	Integer32,
    	    ucOnuMcastStripOption         	Integer32
    	}
    	
   		ucOnuMcastStripSlotIndex OBJECT-TYPE
   	 		SYNTAX  Integer32 (1..16)
     		MAX-ACCESS  read-only
     		STATUS current
     		DESCRIPTION ""
   		::= { ucOnuMcastStripEntry 1 }
   		
   		ucOnuMcastStripPonIndex OBJECT-TYPE
   	 		SYNTAX  Integer32 (1..32)
     		MAX-ACCESS  read-only
     		STATUS current
     		DESCRIPTION ""
   		::= { ucOnuMcastStripEntry 2 }   
       	   
   		ucOnuMcastStripOnuIndex OBJECT-TYPE
   	 		SYNTAX  Integer32 (1..256)
     		MAX-ACCESS  read-only
     		STATUS current
     		DESCRIPTION ""
   		::= { ucOnuMcastStripEntry 3 }
                      
   		ucOnuMcastStripPortIndex OBJECT-TYPE
   	 		SYNTAX  Integer32 (1..256)
     		MAX-ACCESS  read-only
     		STATUS current
     		DESCRIPTION ""
   		::= { ucOnuMcastStripEntry 4 }
           
   		ucOnuMcastStripOption OBJECT-TYPE
   	 		SYNTAX  Integer32 {
   	 		 	onu_unstrip(0),
   	 		 	onu_strip(1)
   	 		}
     		MAX-ACCESS  read-write
     		STATUS current
     		DESCRIPTION
     		"Multicast stream output from ONU , strip tag or remain the tag of frames"    		 
     	::= { ucOnuMcastStripEntry 5 }     	
     	

    	-- 2.6.13.2.1.3
    	ucOnuGroupsMultiVlanTable OBJECT-TYPE
    		SYNTAX SEQUENCE OF UcOnuGroupsMultiVlanEntry
    		MAX-ACCESS not-accessible
    		STATUS mandatory
    		DESCRIPTION "" 
    	::= { ucOnuGroupsCfg 3 }
    	                  
    	-- 2.6.13.2.1.3.1
    	ucOnuGroupsMultiVlanEntry OBJECT-TYPE    
    		SYNTAX UcOnuGroupsMultiVlanEntry
    		MAX-ACCESS not-accessible
    		STATUS mandatory
    		DESCRIPTION ""
    		INDEX { ucOnuGroupsMultiVlanSlotIndex,
    		        ucOnuGroupsMultiVlanPonIndex,
    		        ucOnuGroupsMultiVlanOnuIndex,
    		        ucOnuGroupsMultiVlanPortIndex }
    	::= { ucOnuGroupsMultiVlanTable 1 }
    	
    	UcOnuGroupsMultiVlanEntry ::= SEQUENCE
    	{      
    		ucOnuGroupsMultiVlanSlotIndex	  Integer32,
    		ucOnuGroupsMultiVlanPonIndex	  Integer32,
    		ucOnuGroupsMultiVlanOnuIndex	  Integer32,
    	    ucOnuGroupsMultiVlanPortIndex     Integer32,
    	    ucOnuGroupsMultiVlan              Integer32
       	}
    	
   		ucOnuGroupsMultiVlanSlotIndex OBJECT-TYPE
   	 		SYNTAX  Integer32 (1..16)
     		MAX-ACCESS  read-only
     		STATUS current
     		DESCRIPTION ""
   		::= { ucOnuGroupsMultiVlanEntry 1 }
   		
   		ucOnuGroupsMultiVlanPonIndex OBJECT-TYPE
   	 		SYNTAX  Integer32 (1..32)
     		MAX-ACCESS  read-only
     		STATUS current
     		DESCRIPTION ""
   		::= { ucOnuGroupsMultiVlanEntry 2 }   
       	   
   		ucOnuGroupsMultiVlanOnuIndex OBJECT-TYPE
   	 		SYNTAX  Integer32 (1..256)
     		MAX-ACCESS  read-only
     		STATUS current
     		DESCRIPTION ""
   		::= { ucOnuGroupsMultiVlanEntry 3 }
                      
   		ucOnuGroupsMultiVlanPortIndex OBJECT-TYPE
   	 		SYNTAX  Integer32 (1..256)
     		MAX-ACCESS  read-only
     		STATUS current
     		DESCRIPTION ""
   		::= { ucOnuGroupsMultiVlanEntry 4 }
           
   		ucOnuGroupsMultiVlan OBJECT-TYPE
   	 		SYNTAX  Integer32 (1..4095)
     		MAX-ACCESS  read-write
     		STATUS current
     		DESCRIPTION
     		"Onu Port Multicast VLAN"    		 
     	::= { ucOnuGroupsMultiVlanEntry 5 }     	
     	     	     	
     	
     	
     		
	-- 2.6.13.2.2
	ucOnuGroupsStatus OBJECT IDENTIFIER ::= { ucOnuIgmpGroups 2 }			            
    -- Onu Igmp Multicast Groups with VID
    	-- 2.6.13.2.2.1
    	ucOnuGroupsStatusTable OBJECT-TYPE
    		SYNTAX SEQUENCE OF UcOnuGroupsStatusEntry
    		MAX-ACCESS not-accessible
    		STATUS mandatory
    		DESCRIPTION "" 
    	::= { ucOnuGroupsStatus 1 }
    	
    	-- 2.6.13.2.2.1.1
    	ucOnuGroupsStatusEntry OBJECT-TYPE    
    		SYNTAX UcOnuGroupsStatusEntry
    		MAX-ACCESS not-accessible
    		STATUS mandatory
    		DESCRIPTION ""
    		INDEX { ucOnuGroupsStatusSlotIndex,ucOnuGroupsStatusPonIndex,ucOnuGroupsStatusOnuIndex,ucOnuGroupsStatusPortIndex }
    	::= { ucOnuGroupsStatusTable 1 }
    	
    	UcOnuGroupsStatusEntry ::= SEQUENCE
    	{      
    		ucOnuGroupsStatusSlotIndex		Integer32,
    		ucOnuGroupsStatusPonIndex		Integer32,
    		ucOnuGroupsStatusOnuIndex		Integer32,
    	    ucOnuGroupsStatusPortIndex      Integer32,
    	    ucOnuGroupsStatusGroups         OCTET STRING
    	}
    	
   		ucOnuGroupsStatusSlotIndex OBJECT-TYPE
   	 		SYNTAX  Integer32 (1..16)
     		MAX-ACCESS  read-only
     		STATUS current
     		DESCRIPTION ""
   		::= { ucOnuGroupsStatusEntry 1 }
   		
   		ucOnuGroupsStatusPonIndex OBJECT-TYPE
   	 		SYNTAX  Integer32 (1..32)
     		MAX-ACCESS  read-only
     		STATUS current
     		DESCRIPTION ""
   		::= { ucOnuGroupsStatusEntry 2 }   
       	   
   		ucOnuGroupsStatusOnuIndex OBJECT-TYPE
   	 		SYNTAX  Integer32 (1..256)
     		MAX-ACCESS  read-only
     		STATUS current
     		DESCRIPTION ""
   		::= { ucOnuGroupsStatusEntry 3 }
                      
   		ucOnuGroupsStatusPortIndex OBJECT-TYPE
   	 		SYNTAX  Integer32 (1..256)
     		MAX-ACCESS  read-only
     		STATUS current
     		DESCRIPTION ""
   		::= { ucOnuGroupsStatusEntry 4 }
           
   		ucOnuGroupsStatusGroups OBJECT-TYPE
   	 		SYNTAX  OCTET STRING (SIZE(0..1024))
     		MAX-ACCESS  read-only
     		STATUS current
     		DESCRIPTION
     		"Size ---- Description -------------------------------------------
     		 1          Number of queue sets, Number of times the following fields repeat
     		      ############################################################################################
     		      2     Multicast VLAN ID
     		      6     Multicast Group Mac Address"    		 
     	::= { ucOnuGroupsStatusEntry 5 }     	    
     					                     
-- ######################################################################

	-- Add PON Optic Module Information Mib Branch !!!  
	-- 2017.04.10
  -- 2.6.14
	ucOpticModule OBJECT IDENTIFIER ::= { ucPon 14 }
	
	
-- 2.6.14.1
    	ucOpticModuleOltTable OBJECT-TYPE
    		SYNTAX SEQUENCE OF UcOpticModuleOltEntry
    		MAX-ACCESS not-accessible
    		STATUS mandatory
    		DESCRIPTION "" 
    	::= { ucOpticModule 1 }
    	
    	-- 2.6.14.1.1
    	ucOpticModuleOltEntry OBJECT-TYPE    
    		SYNTAX UcOpticModuleEntry
    		MAX-ACCESS not-accessible
    		STATUS mandatory
    		DESCRIPTION ""
    		INDEX { ucOpticModuleOltSlotIndex,ucOpticModuleOltPonIndex }
    	::= { ucOpticModuleOltTable 1 }
    	
    	UcOpticModuleOltEntry ::= SEQUENCE
    	{      
    		ucOpticModuleOltSlotIndex		Integer32,
    		ucOpticModuleOltPonIndex		Integer32,
    		ucOpticModuleOltTxPower		DisplayString,
    		ucOpticModuleOltVcc		DisplayString,
    		ucOpticModuleOltTxBias		DisplayString,
    		ucOpticModuleOltTemperature		DisplayString
    	}
    	
   		ucOpticModuleOltSlotIndex OBJECT-TYPE
   	 		SYNTAX  Integer32 (1..16)
     		MAX-ACCESS  read-only
     		STATUS current
     		DESCRIPTION ""
   		::= { ucOpticModuleOltEntry 1 }
   		
   		ucOpticModuleOltPonIndex OBJECT-TYPE
   	 		SYNTAX  Integer32 (1..32)
     		MAX-ACCESS  read-only
     		STATUS current
     		DESCRIPTION ""
   		::= { ucOpticModuleOltEntry 2 }   
       	   
   		ucOpticModuleOltTxPower OBJECT-TYPE
   	 		SYNTAX  DisplayString
     		MAX-ACCESS  read-only
     		STATUS current
     		DESCRIPTION "Unit: dBm"
   		::= { ucOpticModuleOltEntry 3 }
                      
   		ucOpticModuleOltVcc OBJECT-TYPE
   	 		SYNTAX  DisplayString
     		MAX-ACCESS  read-only
     		STATUS current
     		DESCRIPTION "Unit: Voltage"
   		::= { ucOpticModuleOltEntry 4 }
           
   		ucOpticModuleOltTxBias OBJECT-TYPE
   	 		SYNTAX  DisplayString
     		MAX-ACCESS  read-only
     		STATUS current
     		DESCRIPTION "Unit: mA"    		 
     	::= { ucOpticModuleOltEntry 5 }	
     	
   		ucOpticModuleOltTemperature OBJECT-TYPE
   	 		SYNTAX  DisplayString
     		MAX-ACCESS  read-only
     		STATUS current
     		DESCRIPTION "Unit: C"    		 
     	::= { ucOpticModuleOltEntry 6 }  
     	


-- 2.6.14.2
    	ucOpticModuleOnuTable OBJECT-TYPE
    		SYNTAX SEQUENCE OF UcOpticModuleOnuEntry
    		MAX-ACCESS not-accessible
    		STATUS mandatory
    		DESCRIPTION "" 
    	::= { ucOpticModule 2 }
    	
    	-- 2.6.14.2.1
    	ucOpticModuleOnuEntry OBJECT-TYPE    
    		SYNTAX UcOpticModuleEntry
    		MAX-ACCESS not-accessible
    		STATUS mandatory
    		DESCRIPTION ""
    		INDEX { ucOpticModuleOnuSlotIndex,ucOpticModuleOnuPonIndex,ucOpticModuleOnuIndex }
    	::= { ucOpticModuleOnuTable 1 }
    	
    	UcOpticModuleOnuEntry ::= SEQUENCE
    	{      
    		ucOpticModuleOnuSlotIndex		Integer32,
    		ucOpticModuleOnuPonIndex		Integer32,
    		ucOpticModuleOnuIndex		Integer32,
    		ucOpticModuleOnuTxPower		DisplayString,
    		ucOpticModuleOnuVcc		DisplayString,
    		ucOpticModuleOnuTxBias		DisplayString,
    		ucOpticModuleOnuTemperature		DisplayString,
    		ucOpticModuleOnuRxPower		DisplayString
    	}
    	
   		ucOpticModuleOnuSlotIndex OBJECT-TYPE
   	 		SYNTAX  Integer32 (1..16)
     		MAX-ACCESS  read-only
     		STATUS current
     		DESCRIPTION ""
   		::= { ucOpticModuleOnuEntry 1 }
   		
   		ucOpticModuleOnuPonIndex OBJECT-TYPE
   	 		SYNTAX  Integer32 (1..32)
     		MAX-ACCESS  read-only
     		STATUS current
     		DESCRIPTION ""
   		::= { ucOpticModuleOnuEntry 2 }   
       	   
   		ucOpticModuleOnuIndex OBJECT-TYPE
   	 		SYNTAX  Integer32 (1..128)
     		MAX-ACCESS  read-only
     		STATUS current
     		DESCRIPTION ""
   		::= { ucOpticModuleOnuEntry 3 }

   		ucOpticModuleOnuTxPower OBJECT-TYPE
   	 		SYNTAX  DisplayString
     		MAX-ACCESS  read-only
     		STATUS current
     		DESCRIPTION "Unit: dBm"
   		::= { ucOpticModuleOnuEntry 4 }
                      
   		ucOpticModuleOnuVcc OBJECT-TYPE
   	 		SYNTAX  DisplayString
     		MAX-ACCESS  read-only
     		STATUS current
     		DESCRIPTION ""
   		::= { ucOpticModuleOnuEntry 5 }
           
   		ucOpticModuleOnuTxBias OBJECT-TYPE
   	 		SYNTAX  DisplayString
     		MAX-ACCESS  read-only
     		STATUS current
     		DESCRIPTION "Unit: mA"    		 
     	::= { ucOpticModuleOnuEntry 6 }	
     	
   		ucOpticModuleOnuTemperature OBJECT-TYPE
   	 		SYNTAX  DisplayString
     		MAX-ACCESS  read-only
     		STATUS current
     		DESCRIPTION "Unit: C"    		 
     	::= { ucOpticModuleOnuEntry 7 } 
     	
     	ucOpticModuleOnuRxPower OBJECT-TYPE
   	 		SYNTAX  DisplayString
     		MAX-ACCESS  read-only
     		STATUS current
     		DESCRIPTION "Unit: dBm"
   		::= { ucOpticModuleOnuEntry 8 }    	   	

-- -------------------------------------------------------------
-- RicherLink ONU with CATV,do the CATV function switch
-- 2019.02.27
-- 2.6.15
-- -------------------------------------------------------------
 
	ucCatv OBJECT IDENTIFIER ::= { ucPon 15 }
	
-- 2.6.15.1
    	ucCatvTable OBJECT-TYPE
    		SYNTAX SEQUENCE OF UcCatvEntry
    		MAX-ACCESS not-accessible
    		STATUS mandatory
    		DESCRIPTION "" 
    	::= { ucCatv 1 }
    	
-- 2.6.15.1.1
    	ucCatvEntry OBJECT-TYPE    
    		SYNTAX UcOpticModuleEntry
    		MAX-ACCESS not-accessible
    		STATUS mandatory
    		DESCRIPTION ""
    		INDEX { ucCatvSlotIndex,ucCatvPonIndex,ucCatvOnuIndex }
    	::= { ucCatvTable 1 }
    	
    	UcCatvEntry ::= SEQUENCE
    	{      
    		ucCatvSlotIndex		Integer32,
    		ucCatvPonIndex		Integer32,
    		ucCatvOnuIndex    Integer32,
    		ucCatvSwitch		  Integer32,    		
    	}
    	
   		ucCatvSlotIndex OBJECT-TYPE
   	 		SYNTAX  Integer32 (1..16)
     		MAX-ACCESS  read-only
     		STATUS current
     		DESCRIPTION ""
   		::= { ucCatvEntry 1 }
   		
   		ucCatvPonIndex OBJECT-TYPE
   	 		SYNTAX  Integer32 (1..32)
     		MAX-ACCESS  read-only
     		STATUS current
     		DESCRIPTION ""
   		::= { ucCatvEntry 2 }
   		
   		ucCatvOnuIndex OBJECT-TYPE
   	 		SYNTAX  Integer32 (1..128)
     		MAX-ACCESS  read-only
     		STATUS current
     		DESCRIPTION ""
   		::= { ucCatvEntry 3 }
       	   
   		ucCatvSwitch OBJECT-TYPE
   	 		SYNTAX  Integer32 {
   	 							  invalid(0),
                    enable(1),
                    disable(2),
                }
     		MAX-ACCESS  read-write
     		STATUS current
     		DESCRIPTION "Trun on/off catv output"
   		::= { ucCatvEntry 4 }

END
